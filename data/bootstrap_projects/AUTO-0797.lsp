(defun c:DrawGeneratedPipe ()
  (setq layer_name "ENG_AUTO-0797")
  (command "_.-LAYER" "_Make" layer_name "")
  (setvar "CLAYER" layer_name)
  (command "_.LINE" "0.000,0.000" "1065.000,0.000" "")
  (command "_.CIRCLE" "0.000,0.000" "256.25")
  (command "_.ARC" "1065.000,0.000" "1065.000,512.500" "1577.500,512.500")
  (command "_.TEXT" "1597.500,-20.000" "5.0" "0" "EMPRESA: Omega Piping")
  (command "_.TEXT" "1597.500,-28.000" "5.0" "0" "PECA: Valve")
  (command "_.TEXT" "1597.500,-36.000" "5.0" "0" "CODIGO: AUTO-0797")
  (princ "\nProjeto gerado com sucesso.")
)
(princ "\nComando carregado: DrawGeneratedPipe")
