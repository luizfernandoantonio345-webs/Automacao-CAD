(defun c:DrawGeneratedPipe ()
  (setq layer_name "ENG_AUTO-0068")
  (command "_.-LAYER" "_Make" layer_name "")
  (setvar "CLAYER" layer_name)
  (command "_.LINE" "0.000,0.000" "575.000,0.000" "")
  (command "_.CIRCLE" "0.000,0.000" "200.0")
  (command "_.ARC" "575.000,0.000" "575.000,400.000" "975.000,400.000")
  (command "_.TEXT" "995.000,-20.000" "5.0" "0" "EMPRESA: Norte Tubulacoes")
  (command "_.TEXT" "995.000,-28.000" "5.0" "0" "PECA: Tee")
  (command "_.TEXT" "995.000,-36.000" "5.0" "0" "CODIGO: AUTO-0068")
  (princ "\nProjeto gerado com sucesso.")
)
(princ "\nComando carregado: DrawGeneratedPipe")
