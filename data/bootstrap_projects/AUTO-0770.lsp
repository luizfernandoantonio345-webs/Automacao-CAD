(defun c:DrawGeneratedPipe ()
  (setq layer_name "ENG_AUTO-0770")
  (command "_.-LAYER" "_Make" layer_name "")
  (setvar "CLAYER" layer_name)
  (command "_.LINE" "0.000,0.000" "120.000,0.000" "")
  (command "_.CIRCLE" "0.000,0.000" "87.5")
  (command "_.ARC" "120.000,0.000" "120.000,175.000" "295.000,175.000")
  (command "_.TEXT" "315.000,-20.000" "5.0" "0" "EMPRESA: Norte Tubulacoes")
  (command "_.TEXT" "315.000,-28.000" "5.0" "0" "PECA: Tee")
  (command "_.TEXT" "315.000,-36.000" "5.0" "0" "CODIGO: AUTO-0770")
  (princ "\nProjeto gerado com sucesso.")
)
(princ "\nComando carregado: DrawGeneratedPipe")
