(defun c:DrawGeneratedPipe ()
  (setq layer_name "ENG_AUTO-0927")
  (command "_.-LAYER" "_Make" layer_name "")
  (setvar "CLAYER" layer_name)
  (command "_.LINE" "0.000,0.000" "1765.000,0.000" "")
  (command "_.CIRCLE" "0.000,0.000" "68.75")
  (command "_.ARC" "1765.000,0.000" "1765.000,137.500" "1902.500,137.500")
  (command "_.TEXT" "1922.500,-20.000" "5.0" "0" "EMPRESA: Sul Processos")
  (command "_.TEXT" "1922.500,-28.000" "5.0" "0" "PECA: Flange")
  (command "_.TEXT" "1922.500,-36.000" "5.0" "0" "CODIGO: AUTO-0927")
  (princ "\nProjeto gerado com sucesso.")
)
(princ "\nComando carregado: DrawGeneratedPipe")
