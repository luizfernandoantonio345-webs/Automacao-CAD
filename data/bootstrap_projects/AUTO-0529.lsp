(defun c:DrawGeneratedPipe ()
  (setq layer_name "ENG_AUTO-0529")
  (command "_.-LAYER" "_Make" layer_name "")
  (setvar "CLAYER" layer_name)
  (command "_.LINE" "0.000,0.000" "1310.000,0.000" "")
  (command "_.CIRCLE" "0.000,0.000" "81.25")
  (command "_.ARC" "1310.000,0.000" "1310.000,162.500" "1472.500,162.500")
  (command "_.TEXT" "1492.500,-20.000" "5.0" "0" "EMPRESA: Engenharia CAD Labs")
  (command "_.TEXT" "1492.500,-28.000" "5.0" "0" "PECA: Curva")
  (command "_.TEXT" "1492.500,-36.000" "5.0" "0" "CODIGO: AUTO-0529")
  (princ "\nProjeto gerado com sucesso.")
)
(princ "\nComando carregado: DrawGeneratedPipe")
