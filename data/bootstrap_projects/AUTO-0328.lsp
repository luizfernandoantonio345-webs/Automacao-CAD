(defun c:DrawGeneratedPipe ()
  (setq layer_name "ENG_AUTO-0328")
  (command "_.-LAYER" "_Make" layer_name "")
  (setvar "CLAYER" layer_name)
  (command "_.LINE" "0.000,0.000" "1975.000,0.000" "")
  (command "_.CIRCLE" "0.000,0.000" "75.0")
  (command "_.ARC" "1975.000,0.000" "1975.000,150.000" "2125.000,150.000")
  (command "_.TEXT" "2145.000,-20.000" "5.0" "0" "EMPRESA: Montreal Plantas")
  (command "_.TEXT" "2145.000,-28.000" "5.0" "0" "PECA: Reducer")
  (command "_.TEXT" "2145.000,-36.000" "5.0" "0" "CODIGO: AUTO-0328")
  (princ "\nProjeto gerado com sucesso.")
)
(princ "\nComando carregado: DrawGeneratedPipe")
