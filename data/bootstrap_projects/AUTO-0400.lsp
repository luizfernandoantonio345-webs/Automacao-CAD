(defun c:DrawGeneratedPipe ()
  (setq layer_name "ENG_AUTO-0400")
  (command "_.-LAYER" "_Make" layer_name "")
  (setvar "CLAYER" layer_name)
  (command "_.LINE" "0.000,0.000" "645.000,0.000" "")
  (command "_.CIRCLE" "0.000,0.000" "25.0")
  (command "_.ARC" "645.000,0.000" "645.000,50.000" "695.000,50.000")
  (command "_.TEXT" "715.000,-20.000" "5.0" "0" "EMPRESA: Montreal Plantas")
  (command "_.TEXT" "715.000,-28.000" "5.0" "0" "PECA: Reducer")
  (command "_.TEXT" "715.000,-36.000" "5.0" "0" "CODIGO: AUTO-0400")
  (princ "\nProjeto gerado com sucesso.")
)
(princ "\nComando carregado: DrawGeneratedPipe")
