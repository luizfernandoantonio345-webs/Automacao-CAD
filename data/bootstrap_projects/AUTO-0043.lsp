(defun c:DrawGeneratedPipe ()
  (setq layer_name "ENG_AUTO-0043")
  (command "_.-LAYER" "_Make" layer_name "")
  (setvar "CLAYER" layer_name)
  (command "_.LINE" "0.000,0.000" "1625.000,0.000" "")
  (command "_.CIRCLE" "0.000,0.000" "43.75")
  (command "_.ARC" "1625.000,0.000" "1625.000,87.500" "1712.500,87.500")
  (command "_.TEXT" "1732.500,-20.000" "5.0" "0" "EMPRESA: Engenharia CAD Labs")
  (command "_.TEXT" "1732.500,-28.000" "5.0" "0" "PECA: Curva")
  (command "_.TEXT" "1732.500,-36.000" "5.0" "0" "CODIGO: AUTO-0043")
  (princ "\nProjeto gerado com sucesso.")
)
(princ "\nComando carregado: DrawGeneratedPipe")
