(defun c:DrawGeneratedPipe ()
  (setq layer_name "ENG_AUTO-1113")
  (command "_.-LAYER" "_Make" layer_name "")
  (setvar "CLAYER" layer_name)
  (command "_.LINE" "0.000,0.000" "575.000,0.000" "")
  (command "_.CIRCLE" "0.000,0.000" "231.25")
  (command "_.ARC" "575.000,0.000" "575.000,462.500" "1037.500,462.500")
  (command "_.TEXT" "1057.500,-20.000" "5.0" "0" "EMPRESA: Sul Processos")
  (command "_.TEXT" "1057.500,-28.000" "5.0" "0" "PECA: Flange")
  (command "_.TEXT" "1057.500,-36.000" "5.0" "0" "CODIGO: AUTO-1113")
  (princ "\nProjeto gerado com sucesso.")
)
(princ "\nComando carregado: DrawGeneratedPipe")
