(defun c:DrawGeneratedPipe ()
  (setq layer_name "ENG_AUTO-0580")
  (command "_.-LAYER" "_Make" layer_name "")
  (setvar "CLAYER" layer_name)
  (command "_.LINE" "0.000,0.000" "1170.000,0.000" "")
  (command "_.CIRCLE" "0.000,0.000" "150.0")
  (command "_.ARC" "1170.000,0.000" "1170.000,300.000" "1470.000,300.000")
  (command "_.TEXT" "1490.000,-20.000" "5.0" "0" "EMPRESA: Montreal Plantas")
  (command "_.TEXT" "1490.000,-28.000" "5.0" "0" "PECA: Reducer")
  (command "_.TEXT" "1490.000,-36.000" "5.0" "0" "CODIGO: AUTO-0580")
  (princ "\nProjeto gerado com sucesso.")
)
(princ "\nComando carregado: DrawGeneratedPipe")
