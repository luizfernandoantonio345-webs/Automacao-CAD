(defun c:DrawGeneratedPipe ()
  (setq layer_name "ENG_AUTO-0833")
  (command "_.-LAYER" "_Make" layer_name "")
  (setvar "CLAYER" layer_name)
  (command "_.LINE" "0.000,0.000" "400.000,0.000" "")
  (command "_.CIRCLE" "0.000,0.000" "231.25")
  (command "_.ARC" "400.000,0.000" "400.000,462.500" "862.500,462.500")
  (command "_.TEXT" "882.500,-20.000" "5.0" "0" "EMPRESA: Omega Piping")
  (command "_.TEXT" "882.500,-28.000" "5.0" "0" "PECA: Valve")
  (command "_.TEXT" "882.500,-36.000" "5.0" "0" "CODIGO: AUTO-0833")
  (princ "\nProjeto gerado com sucesso.")
)
(princ "\nComando carregado: DrawGeneratedPipe")
