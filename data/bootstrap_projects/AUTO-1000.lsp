(defun c:DrawGeneratedPipe ()
  (setq layer_name "ENG_AUTO-1000")
  (command "_.-LAYER" "_Make" layer_name "")
  (setvar "CLAYER" layer_name)
  (command "_.LINE" "0.000,0.000" "470.000,0.000" "")
  (command "_.CIRCLE" "0.000,0.000" "25.0")
  (command "_.ARC" "470.000,0.000" "470.000,50.000" "520.000,50.000")
  (command "_.TEXT" "540.000,-20.000" "5.0" "0" "EMPRESA: Montreal Plantas")
  (command "_.TEXT" "540.000,-28.000" "5.0" "0" "PECA: Reducer")
  (command "_.TEXT" "540.000,-36.000" "5.0" "0" "CODIGO: AUTO-1000")
  (princ "\nProjeto gerado com sucesso.")
)
(princ "\nComando carregado: DrawGeneratedPipe")
