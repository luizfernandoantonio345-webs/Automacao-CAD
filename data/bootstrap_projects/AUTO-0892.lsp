(defun c:DrawGeneratedPipe ()
  (setq layer_name "ENG_AUTO-0892")
  (command "_.-LAYER" "_Make" layer_name "")
  (setvar "CLAYER" layer_name)
  (command "_.LINE" "0.000,0.000" "540.000,0.000" "")
  (command "_.CIRCLE" "0.000,0.000" "100.0")
  (command "_.ARC" "540.000,0.000" "540.000,200.000" "740.000,200.000")
  (command "_.TEXT" "760.000,-20.000" "5.0" "0" "EMPRESA: Montreal Plantas")
  (command "_.TEXT" "760.000,-28.000" "5.0" "0" "PECA: Reducer")
  (command "_.TEXT" "760.000,-36.000" "5.0" "0" "CODIGO: AUTO-0892")
  (princ "\nProjeto gerado com sucesso.")
)
(princ "\nComando carregado: DrawGeneratedPipe")
