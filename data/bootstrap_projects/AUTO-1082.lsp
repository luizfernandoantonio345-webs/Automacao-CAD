(defun c:DrawGeneratedPipe ()
  (setq layer_name "ENG_AUTO-1082")
  (command "_.-LAYER" "_Make" layer_name "")
  (setvar "CLAYER" layer_name)
  (command "_.LINE" "0.000,0.000" "1415.000,0.000" "")
  (command "_.CIRCLE" "0.000,0.000" "37.5")
  (command "_.ARC" "1415.000,0.000" "1415.000,75.000" "1490.000,75.000")
  (command "_.TEXT" "1510.000,-20.000" "5.0" "0" "EMPRESA: Norte Tubulacoes")
  (command "_.TEXT" "1510.000,-28.000" "5.0" "0" "PECA: Tee")
  (command "_.TEXT" "1510.000,-36.000" "5.0" "0" "CODIGO: AUTO-1082")
  (princ "\nProjeto gerado com sucesso.")
)
(princ "\nComando carregado: DrawGeneratedPipe")
