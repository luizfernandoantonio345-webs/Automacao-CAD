(defun c:DrawGeneratedPipe ()
  (setq layer_name "ENG_AUTO-0967")
  (command "_.-LAYER" "_Make" layer_name "")
  (setvar "CLAYER" layer_name)
  (command "_.LINE" "0.000,0.000" "1240.000,0.000" "")
  (command "_.CIRCLE" "0.000,0.000" "68.75")
  (command "_.ARC" "1240.000,0.000" "1240.000,137.500" "1377.500,137.500")
  (command "_.TEXT" "1397.500,-20.000" "5.0" "0" "EMPRESA: Engenharia CAD Labs")
  (command "_.TEXT" "1397.500,-28.000" "5.0" "0" "PECA: Curva")
  (command "_.TEXT" "1397.500,-36.000" "5.0" "0" "CODIGO: AUTO-0967")
  (princ "\nProjeto gerado com sucesso.")
)
(princ "\nComando carregado: DrawGeneratedPipe")
