(defun c:DrawGeneratedPipe ()
  (setq layer_name "ENG_AUTO-0373")
  (command "_.-LAYER" "_Make" layer_name "")
  (setvar "CLAYER" layer_name)
  (command "_.LINE" "0.000,0.000" "1625.000,0.000" "")
  (command "_.CIRCLE" "0.000,0.000" "106.25")
  (command "_.ARC" "1625.000,0.000" "1625.000,212.500" "1837.500,212.500")
  (command "_.TEXT" "1857.500,-20.000" "5.0" "0" "EMPRESA: Engenharia CAD Labs")
  (command "_.TEXT" "1857.500,-28.000" "5.0" "0" "PECA: Curva")
  (command "_.TEXT" "1857.500,-36.000" "5.0" "0" "CODIGO: AUTO-0373")
  (princ "\nProjeto gerado com sucesso.")
)
(princ "\nComando carregado: DrawGeneratedPipe")
