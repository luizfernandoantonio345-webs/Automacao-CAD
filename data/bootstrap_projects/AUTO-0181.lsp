(defun c:DrawGeneratedPipe ()
  (setq layer_name "ENG_AUTO-0181")
  (command "_.-LAYER" "_Make" layer_name "")
  (setvar "CLAYER" layer_name)
  (command "_.LINE" "0.000,0.000" "680.000,0.000" "")
  (command "_.CIRCLE" "0.000,0.000" "156.25")
  (command "_.ARC" "680.000,0.000" "680.000,312.500" "992.500,312.500")
  (command "_.TEXT" "1012.500,-20.000" "5.0" "0" "EMPRESA: Engenharia CAD Labs")
  (command "_.TEXT" "1012.500,-28.000" "5.0" "0" "PECA: Curva")
  (command "_.TEXT" "1012.500,-36.000" "5.0" "0" "CODIGO: AUTO-0181")
  (princ "\nProjeto gerado com sucesso.")
)
(princ "\nComando carregado: DrawGeneratedPipe")
