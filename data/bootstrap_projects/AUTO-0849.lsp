(defun c:DrawGeneratedPipe ()
  (setq layer_name "ENG_AUTO-0849")
  (command "_.-LAYER" "_Make" layer_name "")
  (setvar "CLAYER" layer_name)
  (command "_.LINE" "0.000,0.000" "960.000,0.000" "")
  (command "_.CIRCLE" "0.000,0.000" "81.25")
  (command "_.ARC" "960.000,0.000" "960.000,162.500" "1122.500,162.500")
  (command "_.TEXT" "1142.500,-20.000" "5.0" "0" "EMPRESA: Sul Processos")
  (command "_.TEXT" "1142.500,-28.000" "5.0" "0" "PECA: Flange")
  (command "_.TEXT" "1142.500,-36.000" "5.0" "0" "CODIGO: AUTO-0849")
  (princ "\nProjeto gerado com sucesso.")
)
(princ "\nComando carregado: DrawGeneratedPipe")
