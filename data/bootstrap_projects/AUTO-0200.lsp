(defun c:DrawGeneratedPipe ()
  (setq layer_name "ENG_AUTO-0200")
  (command "_.-LAYER" "_Make" layer_name "")
  (setvar "CLAYER" layer_name)
  (command "_.LINE" "0.000,0.000" "1345.000,0.000" "")
  (command "_.CIRCLE" "0.000,0.000" "25.0")
  (command "_.ARC" "1345.000,0.000" "1345.000,50.000" "1395.000,50.000")
  (command "_.TEXT" "1415.000,-20.000" "5.0" "0" "EMPRESA: Norte Tubulacoes")
  (command "_.TEXT" "1415.000,-28.000" "5.0" "0" "PECA: Tee")
  (command "_.TEXT" "1415.000,-36.000" "5.0" "0" "CODIGO: AUTO-0200")
  (princ "\nProjeto gerado com sucesso.")
)
(princ "\nComando carregado: DrawGeneratedPipe")
