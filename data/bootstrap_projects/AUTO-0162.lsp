(defun c:DrawGeneratedPipe ()
  (setq layer_name "ENG_AUTO-0162")
  (command "_.-LAYER" "_Make" layer_name "")
  (setvar "CLAYER" layer_name)
  (command "_.LINE" "0.000,0.000" "1940.000,0.000" "")
  (command "_.CIRCLE" "0.000,0.000" "37.5")
  (command "_.ARC" "1940.000,0.000" "1940.000,75.000" "2015.000,75.000")
  (command "_.TEXT" "2035.000,-20.000" "5.0" "0" "EMPRESA: Atlas Engenharia")
  (command "_.TEXT" "2035.000,-28.000" "5.0" "0" "PECA: Tubo")
  (command "_.TEXT" "2035.000,-36.000" "5.0" "0" "CODIGO: AUTO-0162")
  (princ "\nProjeto gerado com sucesso.")
)
(princ "\nComando carregado: DrawGeneratedPipe")
