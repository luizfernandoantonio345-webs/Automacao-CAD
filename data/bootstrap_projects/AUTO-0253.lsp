(defun c:DrawGeneratedPipe ()
  (setq layer_name "ENG_AUTO-0253")
  (command "_.-LAYER" "_Make" layer_name "")
  (setvar "CLAYER" layer_name)
  (command "_.LINE" "0.000,0.000" "1275.000,0.000" "")
  (command "_.CIRCLE" "0.000,0.000" "106.25")
  (command "_.ARC" "1275.000,0.000" "1275.000,212.500" "1487.500,212.500")
  (command "_.TEXT" "1507.500,-20.000" "5.0" "0" "EMPRESA: Engenharia CAD Labs")
  (command "_.TEXT" "1507.500,-28.000" "5.0" "0" "PECA: Curva")
  (command "_.TEXT" "1507.500,-36.000" "5.0" "0" "CODIGO: AUTO-0253")
  (princ "\nProjeto gerado com sucesso.")
)
(princ "\nComando carregado: DrawGeneratedPipe")
