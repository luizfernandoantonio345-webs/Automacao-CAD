(defun c:DrawGeneratedPipe ()
  (setq layer_name "ENG_AUTO-1156")
  (command "_.-LAYER" "_Make" layer_name "")
  (setvar "CLAYER" layer_name)
  (command "_.LINE" "0.000,0.000" "155.000,0.000" "")
  (command "_.CIRCLE" "0.000,0.000" "250.0")
  (command "_.ARC" "155.000,0.000" "155.000,500.000" "655.000,500.000")
  (command "_.TEXT" "675.000,-20.000" "5.0" "0" "EMPRESA: Montreal Plantas")
  (command "_.TEXT" "675.000,-28.000" "5.0" "0" "PECA: Reducer")
  (command "_.TEXT" "675.000,-36.000" "5.0" "0" "CODIGO: AUTO-1156")
  (princ "\nProjeto gerado com sucesso.")
)
(princ "\nComando carregado: DrawGeneratedPipe")
