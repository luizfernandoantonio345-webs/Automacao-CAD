(defun c:DrawGeneratedPipe ()
  (setq layer_name "ENG_AUTO-0846")
  (command "_.-LAYER" "_Make" layer_name "")
  (setvar "CLAYER" layer_name)
  (command "_.LINE" "0.000,0.000" "855.000,0.000" "")
  (command "_.CIRCLE" "0.000,0.000" "62.5")
  (command "_.ARC" "855.000,0.000" "855.000,125.000" "980.000,125.000")
  (command "_.TEXT" "1000.000,-20.000" "5.0" "0" "EMPRESA: Atlas Engenharia")
  (command "_.TEXT" "1000.000,-28.000" "5.0" "0" "PECA: Tubo")
  (command "_.TEXT" "1000.000,-36.000" "5.0" "0" "CODIGO: AUTO-0846")
  (princ "\nProjeto gerado com sucesso.")
)
(princ "\nComando carregado: DrawGeneratedPipe")
