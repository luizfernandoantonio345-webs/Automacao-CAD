(defun c:DrawGeneratedPipe ()
  (setq layer_name "ENG_AUTO-1104")
  (command "_.-LAYER" "_Make" layer_name "")
  (setvar "CLAYER" layer_name)
  (command "_.LINE" "0.000,0.000" "260.000,0.000" "")
  (command "_.CIRCLE" "0.000,0.000" "175.0")
  (command "_.ARC" "260.000,0.000" "260.000,350.000" "610.000,350.000")
  (command "_.TEXT" "630.000,-20.000" "5.0" "0" "EMPRESA: Atlas Engenharia")
  (command "_.TEXT" "630.000,-28.000" "5.0" "0" "PECA: Tubo")
  (command "_.TEXT" "630.000,-36.000" "5.0" "0" "CODIGO: AUTO-1104")
  (princ "\nProjeto gerado com sucesso.")
)
(princ "\nComando carregado: DrawGeneratedPipe")
