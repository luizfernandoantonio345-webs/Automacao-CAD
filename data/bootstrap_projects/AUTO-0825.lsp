(defun c:DrawGeneratedPipe ()
  (setq layer_name "ENG_AUTO-0825")
  (command "_.-LAYER" "_Make" layer_name "")
  (setvar "CLAYER" layer_name)
  (command "_.LINE" "0.000,0.000" "120.000,0.000" "")
  (command "_.CIRCLE" "0.000,0.000" "181.25")
  (command "_.ARC" "120.000,0.000" "120.000,362.500" "482.500,362.500")
  (command "_.TEXT" "502.500,-20.000" "5.0" "0" "EMPRESA: Sul Processos")
  (command "_.TEXT" "502.500,-28.000" "5.0" "0" "PECA: Flange")
  (command "_.TEXT" "502.500,-36.000" "5.0" "0" "CODIGO: AUTO-0825")
  (princ "\nProjeto gerado com sucesso.")
)
(princ "\nComando carregado: DrawGeneratedPipe")
