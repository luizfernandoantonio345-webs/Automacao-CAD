(defun c:DrawGeneratedPipe ()
  (setq layer_name "ENG_AUTO-0226")
  (command "_.-LAYER" "_Make" layer_name "")
  (setvar "CLAYER" layer_name)
  (command "_.LINE" "0.000,0.000" "330.000,0.000" "")
  (command "_.CIRCLE" "0.000,0.000" "187.5")
  (command "_.ARC" "330.000,0.000" "330.000,375.000" "705.000,375.000")
  (command "_.TEXT" "725.000,-20.000" "5.0" "0" "EMPRESA: Montreal Plantas")
  (command "_.TEXT" "725.000,-28.000" "5.0" "0" "PECA: Reducer")
  (command "_.TEXT" "725.000,-36.000" "5.0" "0" "CODIGO: AUTO-0226")
  (princ "\nProjeto gerado com sucesso.")
)
(princ "\nComando carregado: DrawGeneratedPipe")
