(defun c:DrawGeneratedPipe ()
  (setq layer_name "ENG_AUTO-0767")
  (command "_.-LAYER" "_Make" layer_name "")
  (setvar "CLAYER" layer_name)
  (command "_.LINE" "0.000,0.000" "1940.000,0.000" "")
  (command "_.CIRCLE" "0.000,0.000" "68.75")
  (command "_.ARC" "1940.000,0.000" "1940.000,137.500" "2077.500,137.500")
  (command "_.TEXT" "2097.500,-20.000" "5.0" "0" "EMPRESA: Omega Piping")
  (command "_.TEXT" "2097.500,-28.000" "5.0" "0" "PECA: Valve")
  (command "_.TEXT" "2097.500,-36.000" "5.0" "0" "CODIGO: AUTO-0767")
  (princ "\nProjeto gerado com sucesso.")
)
(princ "\nComando carregado: DrawGeneratedPipe")
