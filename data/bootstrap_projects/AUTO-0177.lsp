(defun c:DrawGeneratedPipe ()
  (setq layer_name "ENG_AUTO-0177")
  (command "_.-LAYER" "_Make" layer_name "")
  (setvar "CLAYER" layer_name)
  (command "_.LINE" "0.000,0.000" "540.000,0.000" "")
  (command "_.CIRCLE" "0.000,0.000" "131.25")
  (command "_.ARC" "540.000,0.000" "540.000,262.500" "802.500,262.500")
  (command "_.TEXT" "822.500,-20.000" "5.0" "0" "EMPRESA: Sul Processos")
  (command "_.TEXT" "822.500,-28.000" "5.0" "0" "PECA: Flange")
  (command "_.TEXT" "822.500,-36.000" "5.0" "0" "CODIGO: AUTO-0177")
  (princ "\nProjeto gerado com sucesso.")
)
(princ "\nComando carregado: DrawGeneratedPipe")
