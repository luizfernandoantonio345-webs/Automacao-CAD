(defun c:DrawGeneratedPipe ()
  (setq layer_name "ENG_AUTO-0401")
  (command "_.-LAYER" "_Make" layer_name "")
  (setvar "CLAYER" layer_name)
  (command "_.LINE" "0.000,0.000" "680.000,0.000" "")
  (command "_.CIRCLE" "0.000,0.000" "31.25")
  (command "_.ARC" "680.000,0.000" "680.000,62.500" "742.500,62.500")
  (command "_.TEXT" "762.500,-20.000" "5.0" "0" "EMPRESA: Omega Piping")
  (command "_.TEXT" "762.500,-28.000" "5.0" "0" "PECA: Valve")
  (command "_.TEXT" "762.500,-36.000" "5.0" "0" "CODIGO: AUTO-0401")
  (princ "\nProjeto gerado com sucesso.")
)
(princ "\nComando carregado: DrawGeneratedPipe")
