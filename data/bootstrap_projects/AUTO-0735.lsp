(defun c:DrawGeneratedPipe ()
  (setq layer_name "ENG_AUTO-0735")
  (command "_.-LAYER" "_Make" layer_name "")
  (setvar "CLAYER" layer_name)
  (command "_.LINE" "0.000,0.000" "820.000,0.000" "")
  (command "_.CIRCLE" "0.000,0.000" "118.75")
  (command "_.ARC" "820.000,0.000" "820.000,237.500" "1057.500,237.500")
  (command "_.TEXT" "1077.500,-20.000" "5.0" "0" "EMPRESA: Sul Processos")
  (command "_.TEXT" "1077.500,-28.000" "5.0" "0" "PECA: Flange")
  (command "_.TEXT" "1077.500,-36.000" "5.0" "0" "CODIGO: AUTO-0735")
  (princ "\nProjeto gerado com sucesso.")
)
(princ "\nComando carregado: DrawGeneratedPipe")
