(defun c:DrawGeneratedPipe ()
  (setq layer_name "ENG_AUTO-0548")
  (command "_.-LAYER" "_Make" layer_name "")
  (setvar "CLAYER" layer_name)
  (command "_.LINE" "0.000,0.000" "1975.000,0.000" "")
  (command "_.CIRCLE" "0.000,0.000" "200.0")
  (command "_.ARC" "1975.000,0.000" "1975.000,400.000" "2375.000,400.000")
  (command "_.TEXT" "2395.000,-20.000" "5.0" "0" "EMPRESA: Norte Tubulacoes")
  (command "_.TEXT" "2395.000,-28.000" "5.0" "0" "PECA: Tee")
  (command "_.TEXT" "2395.000,-36.000" "5.0" "0" "CODIGO: AUTO-0548")
  (princ "\nProjeto gerado com sucesso.")
)
(princ "\nComando carregado: DrawGeneratedPipe")
