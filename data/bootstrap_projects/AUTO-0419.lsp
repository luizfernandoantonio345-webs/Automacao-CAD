(defun c:DrawGeneratedPipe ()
  (setq layer_name "ENG_AUTO-0419")
  (command "_.-LAYER" "_Make" layer_name "")
  (setvar "CLAYER" layer_name)
  (command "_.LINE" "0.000,0.000" "1310.000,0.000" "")
  (command "_.CIRCLE" "0.000,0.000" "143.75")
  (command "_.ARC" "1310.000,0.000" "1310.000,287.500" "1597.500,287.500")
  (command "_.TEXT" "1617.500,-20.000" "5.0" "0" "EMPRESA: Omega Piping")
  (command "_.TEXT" "1617.500,-28.000" "5.0" "0" "PECA: Valve")
  (command "_.TEXT" "1617.500,-36.000" "5.0" "0" "CODIGO: AUTO-0419")
  (princ "\nProjeto gerado com sucesso.")
)
(princ "\nComando carregado: DrawGeneratedPipe")
