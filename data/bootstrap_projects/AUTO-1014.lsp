(defun c:DrawGeneratedPipe ()
  (setq layer_name "ENG_AUTO-1014")
  (command "_.-LAYER" "_Make" layer_name "")
  (setvar "CLAYER" layer_name)
  (command "_.LINE" "0.000,0.000" "960.000,0.000" "")
  (command "_.CIRCLE" "0.000,0.000" "112.5")
  (command "_.ARC" "960.000,0.000" "960.000,225.000" "1185.000,225.000")
  (command "_.TEXT" "1205.000,-20.000" "5.0" "0" "EMPRESA: Atlas Engenharia")
  (command "_.TEXT" "1205.000,-28.000" "5.0" "0" "PECA: Tubo")
  (command "_.TEXT" "1205.000,-36.000" "5.0" "0" "CODIGO: AUTO-1014")
  (princ "\nProjeto gerado com sucesso.")
)
(princ "\nComando carregado: DrawGeneratedPipe")
