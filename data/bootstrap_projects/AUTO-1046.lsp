(defun c:DrawGeneratedPipe ()
  (setq layer_name "ENG_AUTO-1046")
  (command "_.-LAYER" "_Make" layer_name "")
  (setvar "CLAYER" layer_name)
  (command "_.LINE" "0.000,0.000" "155.000,0.000" "")
  (command "_.CIRCLE" "0.000,0.000" "62.5")
  (command "_.ARC" "155.000,0.000" "155.000,125.000" "280.000,125.000")
  (command "_.TEXT" "300.000,-20.000" "5.0" "0" "EMPRESA: Norte Tubulacoes")
  (command "_.TEXT" "300.000,-28.000" "5.0" "0" "PECA: Tee")
  (command "_.TEXT" "300.000,-36.000" "5.0" "0" "CODIGO: AUTO-1046")
  (princ "\nProjeto gerado com sucesso.")
)
(princ "\nComando carregado: DrawGeneratedPipe")
