(defun c:DrawGeneratedPipe ()
  (setq layer_name "ENG_AUTO-0676")
  (command "_.-LAYER" "_Make" layer_name "")
  (setvar "CLAYER" layer_name)
  (command "_.LINE" "0.000,0.000" "680.000,0.000" "")
  (command "_.CIRCLE" "0.000,0.000" "250.0")
  (command "_.ARC" "680.000,0.000" "680.000,500.000" "1180.000,500.000")
  (command "_.TEXT" "1200.000,-20.000" "5.0" "0" "EMPRESA: Montreal Plantas")
  (command "_.TEXT" "1200.000,-28.000" "5.0" "0" "PECA: Reducer")
  (command "_.TEXT" "1200.000,-36.000" "5.0" "0" "CODIGO: AUTO-0676")
  (princ "\nProjeto gerado com sucesso.")
)
(princ "\nComando carregado: DrawGeneratedPipe")
