(defun c:DrawGeneratedPipe ()
  (setq layer_name "ENG_AUTO-1135")
  (command "_.-LAYER" "_Make" layer_name "")
  (setvar "CLAYER" layer_name)
  (command "_.LINE" "0.000,0.000" "1345.000,0.000" "")
  (command "_.CIRCLE" "0.000,0.000" "118.75")
  (command "_.ARC" "1345.000,0.000" "1345.000,237.500" "1582.500,237.500")
  (command "_.TEXT" "1602.500,-20.000" "5.0" "0" "EMPRESA: Engenharia CAD Labs")
  (command "_.TEXT" "1602.500,-28.000" "5.0" "0" "PECA: Curva")
  (command "_.TEXT" "1602.500,-36.000" "5.0" "0" "CODIGO: AUTO-1135")
  (princ "\nProjeto gerado com sucesso.")
)
(princ "\nComando carregado: DrawGeneratedPipe")
