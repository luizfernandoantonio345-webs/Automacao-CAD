(defun c:DrawGeneratedPipe ()
  (setq layer_name "ENG_AUTO-0361")
  (command "_.-LAYER" "_Make" layer_name "")
  (setvar "CLAYER" layer_name)
  (command "_.LINE" "0.000,0.000" "1205.000,0.000" "")
  (command "_.CIRCLE" "0.000,0.000" "31.25")
  (command "_.ARC" "1205.000,0.000" "1205.000,62.500" "1267.500,62.500")
  (command "_.TEXT" "1287.500,-20.000" "5.0" "0" "EMPRESA: Engenharia CAD Labs")
  (command "_.TEXT" "1287.500,-28.000" "5.0" "0" "PECA: Curva")
  (command "_.TEXT" "1287.500,-36.000" "5.0" "0" "CODIGO: AUTO-0361")
  (princ "\nProjeto gerado com sucesso.")
)
(princ "\nComando carregado: DrawGeneratedPipe")
