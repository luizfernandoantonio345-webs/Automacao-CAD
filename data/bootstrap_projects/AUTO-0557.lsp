(defun c:DrawGeneratedPipe ()
  (setq layer_name "ENG_AUTO-0557")
  (command "_.-LAYER" "_Make" layer_name "")
  (setvar "CLAYER" layer_name)
  (command "_.LINE" "0.000,0.000" "365.000,0.000" "")
  (command "_.CIRCLE" "0.000,0.000" "256.25")
  (command "_.ARC" "365.000,0.000" "365.000,512.500" "877.500,512.500")
  (command "_.TEXT" "897.500,-20.000" "5.0" "0" "EMPRESA: Omega Piping")
  (command "_.TEXT" "897.500,-28.000" "5.0" "0" "PECA: Valve")
  (command "_.TEXT" "897.500,-36.000" "5.0" "0" "CODIGO: AUTO-0557")
  (princ "\nProjeto gerado com sucesso.")
)
(princ "\nComando carregado: DrawGeneratedPipe")
