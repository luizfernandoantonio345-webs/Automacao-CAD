(defun c:DrawGeneratedPipe ()
  (setq layer_name "ENG_AUTO-0359")
  (command "_.-LAYER" "_Make" layer_name "")
  (setvar "CLAYER" layer_name)
  (command "_.LINE" "0.000,0.000" "1135.000,0.000" "")
  (command "_.CIRCLE" "0.000,0.000" "268.75")
  (command "_.ARC" "1135.000,0.000" "1135.000,537.500" "1672.500,537.500")
  (command "_.TEXT" "1692.500,-20.000" "5.0" "0" "EMPRESA: Omega Piping")
  (command "_.TEXT" "1692.500,-28.000" "5.0" "0" "PECA: Valve")
  (command "_.TEXT" "1692.500,-36.000" "5.0" "0" "CODIGO: AUTO-0359")
  (princ "\nProjeto gerado com sucesso.")
)
(princ "\nComando carregado: DrawGeneratedPipe")
