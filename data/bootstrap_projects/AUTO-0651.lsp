(defun c:DrawGeneratedPipe ()
  (setq layer_name "ENG_AUTO-0651")
  (command "_.-LAYER" "_Make" layer_name "")
  (setvar "CLAYER" layer_name)
  (command "_.LINE" "0.000,0.000" "1730.000,0.000" "")
  (command "_.CIRCLE" "0.000,0.000" "93.75")
  (command "_.ARC" "1730.000,0.000" "1730.000,187.500" "1917.500,187.500")
  (command "_.TEXT" "1937.500,-20.000" "5.0" "0" "EMPRESA: Sul Processos")
  (command "_.TEXT" "1937.500,-28.000" "5.0" "0" "PECA: Flange")
  (command "_.TEXT" "1937.500,-36.000" "5.0" "0" "CODIGO: AUTO-0651")
  (princ "\nProjeto gerado com sucesso.")
)
(princ "\nComando carregado: DrawGeneratedPipe")
