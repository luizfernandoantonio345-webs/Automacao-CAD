(defun c:DrawGeneratedPipe ()
  (setq layer_name "ENG_AUTO-1129")
  (command "_.-LAYER" "_Make" layer_name "")
  (setvar "CLAYER" layer_name)
  (command "_.LINE" "0.000,0.000" "1135.000,0.000" "")
  (command "_.CIRCLE" "0.000,0.000" "81.25")
  (command "_.ARC" "1135.000,0.000" "1135.000,162.500" "1297.500,162.500")
  (command "_.TEXT" "1317.500,-20.000" "5.0" "0" "EMPRESA: Engenharia CAD Labs")
  (command "_.TEXT" "1317.500,-28.000" "5.0" "0" "PECA: Curva")
  (command "_.TEXT" "1317.500,-36.000" "5.0" "0" "CODIGO: AUTO-1129")
  (princ "\nProjeto gerado com sucesso.")
)
(princ "\nComando carregado: DrawGeneratedPipe")
