(defun c:DrawGeneratedPipe ()
  (setq layer_name "ENG_AUTO-1143")
  (command "_.-LAYER" "_Make" layer_name "")
  (setvar "CLAYER" layer_name)
  (command "_.LINE" "0.000,0.000" "1625.000,0.000" "")
  (command "_.CIRCLE" "0.000,0.000" "168.75")
  (command "_.ARC" "1625.000,0.000" "1625.000,337.500" "1962.500,337.500")
  (command "_.TEXT" "1982.500,-20.000" "5.0" "0" "EMPRESA: Sul Processos")
  (command "_.TEXT" "1982.500,-28.000" "5.0" "0" "PECA: Flange")
  (command "_.TEXT" "1982.500,-36.000" "5.0" "0" "CODIGO: AUTO-1143")
  (princ "\nProjeto gerado com sucesso.")
)
(princ "\nComando carregado: DrawGeneratedPipe")
