(defun c:DrawGeneratedPipe ()
  (setq layer_name "ENG_AUTO-0340")
  (command "_.-LAYER" "_Make" layer_name "")
  (setvar "CLAYER" layer_name)
  (command "_.LINE" "0.000,0.000" "470.000,0.000" "")
  (command "_.CIRCLE" "0.000,0.000" "150.0")
  (command "_.ARC" "470.000,0.000" "470.000,300.000" "770.000,300.000")
  (command "_.TEXT" "790.000,-20.000" "5.0" "0" "EMPRESA: Montreal Plantas")
  (command "_.TEXT" "790.000,-28.000" "5.0" "0" "PECA: Reducer")
  (command "_.TEXT" "790.000,-36.000" "5.0" "0" "CODIGO: AUTO-0340")
  (princ "\nProjeto gerado com sucesso.")
)
(princ "\nComando carregado: DrawGeneratedPipe")
