(defun c:DrawGeneratedPipe ()
  (setq layer_name "ENG_AUTO-1136")
  (command "_.-LAYER" "_Make" layer_name "")
  (setvar "CLAYER" layer_name)
  (command "_.LINE" "0.000,0.000" "1380.000,0.000" "")
  (command "_.CIRCLE" "0.000,0.000" "125.0")
  (command "_.ARC" "1380.000,0.000" "1380.000,250.000" "1630.000,250.000")
  (command "_.TEXT" "1650.000,-20.000" "5.0" "0" "EMPRESA: Norte Tubulacoes")
  (command "_.TEXT" "1650.000,-28.000" "5.0" "0" "PECA: Tee")
  (command "_.TEXT" "1650.000,-36.000" "5.0" "0" "CODIGO: AUTO-1136")
  (princ "\nProjeto gerado com sucesso.")
)
(princ "\nComando carregado: DrawGeneratedPipe")
