(defun c:DrawGeneratedPipe ()
  (setq layer_name "ENG_AUTO-0308")
  (command "_.-LAYER" "_Make" layer_name "")
  (setvar "CLAYER" layer_name)
  (command "_.LINE" "0.000,0.000" "1275.000,0.000" "")
  (command "_.CIRCLE" "0.000,0.000" "200.0")
  (command "_.ARC" "1275.000,0.000" "1275.000,400.000" "1675.000,400.000")
  (command "_.TEXT" "1695.000,-20.000" "5.0" "0" "EMPRESA: Norte Tubulacoes")
  (command "_.TEXT" "1695.000,-28.000" "5.0" "0" "PECA: Tee")
  (command "_.TEXT" "1695.000,-36.000" "5.0" "0" "CODIGO: AUTO-0308")
  (princ "\nProjeto gerado com sucesso.")
)
(princ "\nComando carregado: DrawGeneratedPipe")
