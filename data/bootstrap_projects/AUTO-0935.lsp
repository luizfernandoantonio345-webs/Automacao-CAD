(defun c:DrawGeneratedPipe ()
  (setq layer_name "ENG_AUTO-0935")
  (command "_.-LAYER" "_Make" layer_name "")
  (setvar "CLAYER" layer_name)
  (command "_.LINE" "0.000,0.000" "120.000,0.000" "")
  (command "_.CIRCLE" "0.000,0.000" "118.75")
  (command "_.ARC" "120.000,0.000" "120.000,237.500" "357.500,237.500")
  (command "_.TEXT" "377.500,-20.000" "5.0" "0" "EMPRESA: Omega Piping")
  (command "_.TEXT" "377.500,-28.000" "5.0" "0" "PECA: Valve")
  (command "_.TEXT" "377.500,-36.000" "5.0" "0" "CODIGO: AUTO-0935")
  (princ "\nProjeto gerado com sucesso.")
)
(princ "\nComando carregado: DrawGeneratedPipe")
