(defun c:DrawGeneratedPipe ()
  (setq layer_name "ENG_AUTO-1084")
  (command "_.-LAYER" "_Make" layer_name "")
  (setvar "CLAYER" layer_name)
  (command "_.LINE" "0.000,0.000" "1485.000,0.000" "")
  (command "_.CIRCLE" "0.000,0.000" "50.0")
  (command "_.ARC" "1485.000,0.000" "1485.000,100.000" "1585.000,100.000")
  (command "_.TEXT" "1605.000,-20.000" "5.0" "0" "EMPRESA: Montreal Plantas")
  (command "_.TEXT" "1605.000,-28.000" "5.0" "0" "PECA: Reducer")
  (command "_.TEXT" "1605.000,-36.000" "5.0" "0" "CODIGO: AUTO-1084")
  (princ "\nProjeto gerado com sucesso.")
)
(princ "\nComando carregado: DrawGeneratedPipe")
