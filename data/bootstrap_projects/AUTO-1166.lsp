(defun c:DrawGeneratedPipe ()
  (setq layer_name "ENG_AUTO-1166")
  (command "_.-LAYER" "_Make" layer_name "")
  (setvar "CLAYER" layer_name)
  (command "_.LINE" "0.000,0.000" "505.000,0.000" "")
  (command "_.CIRCLE" "0.000,0.000" "62.5")
  (command "_.ARC" "505.000,0.000" "505.000,125.000" "630.000,125.000")
  (command "_.TEXT" "650.000,-20.000" "5.0" "0" "EMPRESA: Norte Tubulacoes")
  (command "_.TEXT" "650.000,-28.000" "5.0" "0" "PECA: Tee")
  (command "_.TEXT" "650.000,-36.000" "5.0" "0" "CODIGO: AUTO-1166")
  (princ "\nProjeto gerado com sucesso.")
)
(princ "\nComando carregado: DrawGeneratedPipe")
