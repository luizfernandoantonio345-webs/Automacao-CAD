(defun c:DrawGeneratedPipe ()
  (setq layer_name "ENG_AUTO-0185")
  (command "_.-LAYER" "_Make" layer_name "")
  (setvar "CLAYER" layer_name)
  (command "_.LINE" "0.000,0.000" "820.000,0.000" "")
  (command "_.CIRCLE" "0.000,0.000" "181.25")
  (command "_.ARC" "820.000,0.000" "820.000,362.500" "1182.500,362.500")
  (command "_.TEXT" "1202.500,-20.000" "5.0" "0" "EMPRESA: Omega Piping")
  (command "_.TEXT" "1202.500,-28.000" "5.0" "0" "PECA: Valve")
  (command "_.TEXT" "1202.500,-36.000" "5.0" "0" "CODIGO: AUTO-0185")
  (princ "\nProjeto gerado com sucesso.")
)
(princ "\nComando carregado: DrawGeneratedPipe")
