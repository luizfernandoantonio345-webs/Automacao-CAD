(defun c:DrawGeneratedPipe ()
  (setq layer_name "ENG_AUTO-0386")
  (command "_.-LAYER" "_Make" layer_name "")
  (setvar "CLAYER" layer_name)
  (command "_.LINE" "0.000,0.000" "155.000,0.000" "")
  (command "_.CIRCLE" "0.000,0.000" "187.5")
  (command "_.ARC" "155.000,0.000" "155.000,375.000" "530.000,375.000")
  (command "_.TEXT" "550.000,-20.000" "5.0" "0" "EMPRESA: Norte Tubulacoes")
  (command "_.TEXT" "550.000,-28.000" "5.0" "0" "PECA: Tee")
  (command "_.TEXT" "550.000,-36.000" "5.0" "0" "CODIGO: AUTO-0386")
  (princ "\nProjeto gerado com sucesso.")
)
(princ "\nComando carregado: DrawGeneratedPipe")
