(defun c:DrawGeneratedPipe ()
  (setq layer_name "ENG_AUTO-0937")
  (command "_.-LAYER" "_Make" layer_name "")
  (setvar "CLAYER" layer_name)
  (command "_.LINE" "0.000,0.000" "190.000,0.000" "")
  (command "_.CIRCLE" "0.000,0.000" "131.25")
  (command "_.ARC" "190.000,0.000" "190.000,262.500" "452.500,262.500")
  (command "_.TEXT" "472.500,-20.000" "5.0" "0" "EMPRESA: Engenharia CAD Labs")
  (command "_.TEXT" "472.500,-28.000" "5.0" "0" "PECA: Curva")
  (command "_.TEXT" "472.500,-36.000" "5.0" "0" "CODIGO: AUTO-0937")
  (princ "\nProjeto gerado com sucesso.")
)
(princ "\nComando carregado: DrawGeneratedPipe")
