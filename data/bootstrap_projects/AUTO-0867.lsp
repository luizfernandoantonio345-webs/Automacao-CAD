(defun c:DrawGeneratedPipe ()
  (setq layer_name "ENG_AUTO-0867")
  (command "_.-LAYER" "_Make" layer_name "")
  (setvar "CLAYER" layer_name)
  (command "_.LINE" "0.000,0.000" "1590.000,0.000" "")
  (command "_.CIRCLE" "0.000,0.000" "193.75")
  (command "_.ARC" "1590.000,0.000" "1590.000,387.500" "1977.500,387.500")
  (command "_.TEXT" "1997.500,-20.000" "5.0" "0" "EMPRESA: Sul Processos")
  (command "_.TEXT" "1997.500,-28.000" "5.0" "0" "PECA: Flange")
  (command "_.TEXT" "1997.500,-36.000" "5.0" "0" "CODIGO: AUTO-0867")
  (princ "\nProjeto gerado com sucesso.")
)
(princ "\nComando carregado: DrawGeneratedPipe")
