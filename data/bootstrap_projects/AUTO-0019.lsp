(defun c:DrawGeneratedPipe ()
  (setq layer_name "ENG_AUTO-0019")
  (command "_.-LAYER" "_Make" layer_name "")
  (setvar "CLAYER" layer_name)
  (command "_.LINE" "0.000,0.000" "785.000,0.000" "")
  (command "_.CIRCLE" "0.000,0.000" "143.75")
  (command "_.ARC" "785.000,0.000" "785.000,287.500" "1072.500,287.500")
  (command "_.TEXT" "1092.500,-20.000" "5.0" "0" "EMPRESA: Engenharia CAD Labs")
  (command "_.TEXT" "1092.500,-28.000" "5.0" "0" "PECA: Curva")
  (command "_.TEXT" "1092.500,-36.000" "5.0" "0" "CODIGO: AUTO-0019")
  (princ "\nProjeto gerado com sucesso.")
)
(princ "\nComando carregado: DrawGeneratedPipe")
