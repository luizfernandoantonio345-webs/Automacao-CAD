(defun c:DrawGeneratedPipe ()
  (setq layer_name "ENG_AUTO-0588")
  (command "_.-LAYER" "_Make" layer_name "")
  (setvar "CLAYER" layer_name)
  (command "_.LINE" "0.000,0.000" "1450.000,0.000" "")
  (command "_.CIRCLE" "0.000,0.000" "200.0")
  (command "_.ARC" "1450.000,0.000" "1450.000,400.000" "1850.000,400.000")
  (command "_.TEXT" "1870.000,-20.000" "5.0" "0" "EMPRESA: Atlas Engenharia")
  (command "_.TEXT" "1870.000,-28.000" "5.0" "0" "PECA: Tubo")
  (command "_.TEXT" "1870.000,-36.000" "5.0" "0" "CODIGO: AUTO-0588")
  (princ "\nProjeto gerado com sucesso.")
)
(princ "\nComando carregado: DrawGeneratedPipe")
