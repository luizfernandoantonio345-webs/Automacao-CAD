(defun c:DrawGeneratedPipe ()
  (setq layer_name "ENG_AUTO-0488")
  (command "_.-LAYER" "_Make" layer_name "")
  (setvar "CLAYER" layer_name)
  (command "_.LINE" "0.000,0.000" "1800.000,0.000" "")
  (command "_.CIRCLE" "0.000,0.000" "75.0")
  (command "_.ARC" "1800.000,0.000" "1800.000,150.000" "1950.000,150.000")
  (command "_.TEXT" "1970.000,-20.000" "5.0" "0" "EMPRESA: Norte Tubulacoes")
  (command "_.TEXT" "1970.000,-28.000" "5.0" "0" "PECA: Tee")
  (command "_.TEXT" "1970.000,-36.000" "5.0" "0" "CODIGO: AUTO-0488")
  (princ "\nProjeto gerado com sucesso.")
)
(princ "\nComando carregado: DrawGeneratedPipe")
