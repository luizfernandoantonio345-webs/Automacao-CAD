(defun c:DrawGeneratedPipe ()
  (setq layer_name "ENG_AUTO-0572")
  (command "_.-LAYER" "_Make" layer_name "")
  (setvar "CLAYER" layer_name)
  (command "_.LINE" "0.000,0.000" "890.000,0.000" "")
  (command "_.CIRCLE" "0.000,0.000" "100.0")
  (command "_.ARC" "890.000,0.000" "890.000,200.000" "1090.000,200.000")
  (command "_.TEXT" "1110.000,-20.000" "5.0" "0" "EMPRESA: Norte Tubulacoes")
  (command "_.TEXT" "1110.000,-28.000" "5.0" "0" "PECA: Tee")
  (command "_.TEXT" "1110.000,-36.000" "5.0" "0" "CODIGO: AUTO-0572")
  (princ "\nProjeto gerado com sucesso.")
)
(princ "\nComando carregado: DrawGeneratedPipe")
