(defun c:DrawGeneratedPipe ()
  (setq layer_name "ENG_AUTO-0581")
  (command "_.-LAYER" "_Make" layer_name "")
  (setvar "CLAYER" layer_name)
  (command "_.LINE" "0.000,0.000" "1205.000,0.000" "")
  (command "_.CIRCLE" "0.000,0.000" "156.25")
  (command "_.ARC" "1205.000,0.000" "1205.000,312.500" "1517.500,312.500")
  (command "_.TEXT" "1537.500,-20.000" "5.0" "0" "EMPRESA: Omega Piping")
  (command "_.TEXT" "1537.500,-28.000" "5.0" "0" "PECA: Valve")
  (command "_.TEXT" "1537.500,-36.000" "5.0" "0" "CODIGO: AUTO-0581")
  (princ "\nProjeto gerado com sucesso.")
)
(princ "\nComando carregado: DrawGeneratedPipe")
