(defun c:DrawGeneratedPipe ()
  (setq layer_name "ENG_AUTO-1092")
  (command "_.-LAYER" "_Make" layer_name "")
  (setvar "CLAYER" layer_name)
  (command "_.LINE" "0.000,0.000" "1765.000,0.000" "")
  (command "_.CIRCLE" "0.000,0.000" "100.0")
  (command "_.ARC" "1765.000,0.000" "1765.000,200.000" "1965.000,200.000")
  (command "_.TEXT" "1985.000,-20.000" "5.0" "0" "EMPRESA: Atlas Engenharia")
  (command "_.TEXT" "1985.000,-28.000" "5.0" "0" "PECA: Tubo")
  (command "_.TEXT" "1985.000,-36.000" "5.0" "0" "CODIGO: AUTO-1092")
  (princ "\nProjeto gerado com sucesso.")
)
(princ "\nComando carregado: DrawGeneratedPipe")
