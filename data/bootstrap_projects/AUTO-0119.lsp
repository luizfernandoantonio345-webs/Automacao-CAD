(defun c:DrawGeneratedPipe ()
  (setq layer_name "ENG_AUTO-0119")
  (command "_.-LAYER" "_Make" layer_name "")
  (setvar "CLAYER" layer_name)
  (command "_.LINE" "0.000,0.000" "435.000,0.000" "")
  (command "_.CIRCLE" "0.000,0.000" "268.75")
  (command "_.ARC" "435.000,0.000" "435.000,537.500" "972.500,537.500")
  (command "_.TEXT" "992.500,-20.000" "5.0" "0" "EMPRESA: Omega Piping")
  (command "_.TEXT" "992.500,-28.000" "5.0" "0" "PECA: Valve")
  (command "_.TEXT" "992.500,-36.000" "5.0" "0" "CODIGO: AUTO-0119")
  (princ "\nProjeto gerado com sucesso.")
)
(princ "\nComando carregado: DrawGeneratedPipe")
