(defun c:DrawGeneratedPipe ()
  (setq layer_name "ENG_AUTO-0878")
  (command "_.-LAYER" "_Make" layer_name "")
  (setvar "CLAYER" layer_name)
  (command "_.LINE" "0.000,0.000" "1975.000,0.000" "")
  (command "_.CIRCLE" "0.000,0.000" "262.5")
  (command "_.ARC" "1975.000,0.000" "1975.000,525.000" "2500.000,525.000")
  (command "_.TEXT" "2520.000,-20.000" "5.0" "0" "EMPRESA: Norte Tubulacoes")
  (command "_.TEXT" "2520.000,-28.000" "5.0" "0" "PECA: Tee")
  (command "_.TEXT" "2520.000,-36.000" "5.0" "0" "CODIGO: AUTO-0878")
  (princ "\nProjeto gerado com sucesso.")
)
(princ "\nComando carregado: DrawGeneratedPipe")
