(defun c:DrawGeneratedPipe ()
  (setq layer_name "ENG_AUTO-0445")
  (command "_.-LAYER" "_Make" layer_name "")
  (setvar "CLAYER" layer_name)
  (command "_.LINE" "0.000,0.000" "295.000,0.000" "")
  (command "_.CIRCLE" "0.000,0.000" "56.25")
  (command "_.ARC" "295.000,0.000" "295.000,112.500" "407.500,112.500")
  (command "_.TEXT" "427.500,-20.000" "5.0" "0" "EMPRESA: Engenharia CAD Labs")
  (command "_.TEXT" "427.500,-28.000" "5.0" "0" "PECA: Curva")
  (command "_.TEXT" "427.500,-36.000" "5.0" "0" "CODIGO: AUTO-0445")
  (princ "\nProjeto gerado com sucesso.")
)
(princ "\nComando carregado: DrawGeneratedPipe")
