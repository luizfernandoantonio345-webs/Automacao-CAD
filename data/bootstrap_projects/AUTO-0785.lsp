(defun c:DrawGeneratedPipe ()
  (setq layer_name "ENG_AUTO-0785")
  (command "_.-LAYER" "_Make" layer_name "")
  (setvar "CLAYER" layer_name)
  (command "_.LINE" "0.000,0.000" "645.000,0.000" "")
  (command "_.CIRCLE" "0.000,0.000" "181.25")
  (command "_.ARC" "645.000,0.000" "645.000,362.500" "1007.500,362.500")
  (command "_.TEXT" "1027.500,-20.000" "5.0" "0" "EMPRESA: Omega Piping")
  (command "_.TEXT" "1027.500,-28.000" "5.0" "0" "PECA: Valve")
  (command "_.TEXT" "1027.500,-36.000" "5.0" "0" "CODIGO: AUTO-0785")
  (princ "\nProjeto gerado com sucesso.")
)
(princ "\nComando carregado: DrawGeneratedPipe")
