(defun c:DrawGeneratedPipe ()
  (setq layer_name "ENG_AUTO-0874")
  (command "_.-LAYER" "_Make" layer_name "")
  (setvar "CLAYER" layer_name)
  (command "_.LINE" "0.000,0.000" "1835.000,0.000" "")
  (command "_.CIRCLE" "0.000,0.000" "237.5")
  (command "_.ARC" "1835.000,0.000" "1835.000,475.000" "2310.000,475.000")
  (command "_.TEXT" "2330.000,-20.000" "5.0" "0" "EMPRESA: Montreal Plantas")
  (command "_.TEXT" "2330.000,-28.000" "5.0" "0" "PECA: Reducer")
  (command "_.TEXT" "2330.000,-36.000" "5.0" "0" "CODIGO: AUTO-0874")
  (princ "\nProjeto gerado com sucesso.")
)
(princ "\nComando carregado: DrawGeneratedPipe")
