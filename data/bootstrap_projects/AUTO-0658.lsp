(defun c:DrawGeneratedPipe ()
  (setq layer_name "ENG_AUTO-0658")
  (command "_.-LAYER" "_Make" layer_name "")
  (setvar "CLAYER" layer_name)
  (command "_.LINE" "0.000,0.000" "1975.000,0.000" "")
  (command "_.CIRCLE" "0.000,0.000" "137.5")
  (command "_.ARC" "1975.000,0.000" "1975.000,275.000" "2250.000,275.000")
  (command "_.TEXT" "2270.000,-20.000" "5.0" "0" "EMPRESA: Montreal Plantas")
  (command "_.TEXT" "2270.000,-28.000" "5.0" "0" "PECA: Reducer")
  (command "_.TEXT" "2270.000,-36.000" "5.0" "0" "CODIGO: AUTO-0658")
  (princ "\nProjeto gerado com sucesso.")
)
(princ "\nComando carregado: DrawGeneratedPipe")
