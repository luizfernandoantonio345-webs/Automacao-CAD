(defun c:DrawGeneratedPipe ()
  (setq layer_name "ENG_AUTO-0396")
  (command "_.-LAYER" "_Make" layer_name "")
  (setvar "CLAYER" layer_name)
  (command "_.LINE" "0.000,0.000" "505.000,0.000" "")
  (command "_.CIRCLE" "0.000,0.000" "250.0")
  (command "_.ARC" "505.000,0.000" "505.000,500.000" "1005.000,500.000")
  (command "_.TEXT" "1025.000,-20.000" "5.0" "0" "EMPRESA: Atlas Engenharia")
  (command "_.TEXT" "1025.000,-28.000" "5.0" "0" "PECA: Tubo")
  (command "_.TEXT" "1025.000,-36.000" "5.0" "0" "CODIGO: AUTO-0396")
  (princ "\nProjeto gerado com sucesso.")
)
(princ "\nComando carregado: DrawGeneratedPipe")
