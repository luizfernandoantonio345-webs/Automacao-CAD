(defun c:DrawGeneratedPipe ()
  (setq layer_name "ENG_AUTO-0600")
  (command "_.-LAYER" "_Make" layer_name "")
  (setvar "CLAYER" layer_name)
  (command "_.LINE" "0.000,0.000" "1870.000,0.000" "")
  (command "_.CIRCLE" "0.000,0.000" "25.0")
  (command "_.ARC" "1870.000,0.000" "1870.000,50.000" "1920.000,50.000")
  (command "_.TEXT" "1940.000,-20.000" "5.0" "0" "EMPRESA: Atlas Engenharia")
  (command "_.TEXT" "1940.000,-28.000" "5.0" "0" "PECA: Tubo")
  (command "_.TEXT" "1940.000,-36.000" "5.0" "0" "CODIGO: AUTO-0600")
  (princ "\nProjeto gerado com sucesso.")
)
(princ "\nComando carregado: DrawGeneratedPipe")
