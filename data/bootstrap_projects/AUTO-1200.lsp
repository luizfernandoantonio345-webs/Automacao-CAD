(defun c:DrawGeneratedPipe ()
  (setq layer_name "ENG_AUTO-1200")
  (command "_.-LAYER" "_Make" layer_name "")
  (setvar "CLAYER" layer_name)
  (command "_.LINE" "0.000,0.000" "1695.000,0.000" "")
  (command "_.CIRCLE" "0.000,0.000" "25.0")
  (command "_.ARC" "1695.000,0.000" "1695.000,50.000" "1745.000,50.000")
  (command "_.TEXT" "1765.000,-20.000" "5.0" "0" "EMPRESA: Atlas Engenharia")
  (command "_.TEXT" "1765.000,-28.000" "5.0" "0" "PECA: Tubo")
  (command "_.TEXT" "1765.000,-36.000" "5.0" "0" "CODIGO: AUTO-1200")
  (princ "\nProjeto gerado com sucesso.")
)
(princ "\nComando carregado: DrawGeneratedPipe")
