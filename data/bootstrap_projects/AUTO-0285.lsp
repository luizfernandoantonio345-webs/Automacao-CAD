(defun c:DrawGeneratedPipe ()
  (setq layer_name "ENG_AUTO-0285")
  (command "_.-LAYER" "_Make" layer_name "")
  (setvar "CLAYER" layer_name)
  (command "_.LINE" "0.000,0.000" "470.000,0.000" "")
  (command "_.CIRCLE" "0.000,0.000" "56.25")
  (command "_.ARC" "470.000,0.000" "470.000,112.500" "582.500,112.500")
  (command "_.TEXT" "602.500,-20.000" "5.0" "0" "EMPRESA: Sul Processos")
  (command "_.TEXT" "602.500,-28.000" "5.0" "0" "PECA: Flange")
  (command "_.TEXT" "602.500,-36.000" "5.0" "0" "CODIGO: AUTO-0285")
  (princ "\nProjeto gerado com sucesso.")
)
(princ "\nComando carregado: DrawGeneratedPipe")
