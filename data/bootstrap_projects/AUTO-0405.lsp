(defun c:DrawGeneratedPipe ()
  (setq layer_name "ENG_AUTO-0405")
  (command "_.-LAYER" "_Make" layer_name "")
  (setvar "CLAYER" layer_name)
  (command "_.LINE" "0.000,0.000" "820.000,0.000" "")
  (command "_.CIRCLE" "0.000,0.000" "56.25")
  (command "_.ARC" "820.000,0.000" "820.000,112.500" "932.500,112.500")
  (command "_.TEXT" "952.500,-20.000" "5.0" "0" "EMPRESA: Sul Processos")
  (command "_.TEXT" "952.500,-28.000" "5.0" "0" "PECA: Flange")
  (command "_.TEXT" "952.500,-36.000" "5.0" "0" "CODIGO: AUTO-0405")
  (princ "\nProjeto gerado com sucesso.")
)
(princ "\nComando carregado: DrawGeneratedPipe")
