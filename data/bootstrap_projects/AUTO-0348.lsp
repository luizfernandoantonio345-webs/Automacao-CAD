(defun c:DrawGeneratedPipe ()
  (setq layer_name "ENG_AUTO-0348")
  (command "_.-LAYER" "_Make" layer_name "")
  (setvar "CLAYER" layer_name)
  (command "_.LINE" "0.000,0.000" "750.000,0.000" "")
  (command "_.CIRCLE" "0.000,0.000" "200.0")
  (command "_.ARC" "750.000,0.000" "750.000,400.000" "1150.000,400.000")
  (command "_.TEXT" "1170.000,-20.000" "5.0" "0" "EMPRESA: Atlas Engenharia")
  (command "_.TEXT" "1170.000,-28.000" "5.0" "0" "PECA: Tubo")
  (command "_.TEXT" "1170.000,-36.000" "5.0" "0" "CODIGO: AUTO-0348")
  (princ "\nProjeto gerado com sucesso.")
)
(princ "\nComando carregado: DrawGeneratedPipe")
