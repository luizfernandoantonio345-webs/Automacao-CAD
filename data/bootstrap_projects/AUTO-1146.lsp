(defun c:DrawGeneratedPipe ()
  (setq layer_name "ENG_AUTO-1146")
  (command "_.-LAYER" "_Make" layer_name "")
  (setvar "CLAYER" layer_name)
  (command "_.LINE" "0.000,0.000" "1730.000,0.000" "")
  (command "_.CIRCLE" "0.000,0.000" "187.5")
  (command "_.ARC" "1730.000,0.000" "1730.000,375.000" "2105.000,375.000")
  (command "_.TEXT" "2125.000,-20.000" "5.0" "0" "EMPRESA: Atlas Engenharia")
  (command "_.TEXT" "2125.000,-28.000" "5.0" "0" "PECA: Tubo")
  (command "_.TEXT" "2125.000,-36.000" "5.0" "0" "CODIGO: AUTO-1146")
  (princ "\nProjeto gerado com sucesso.")
)
(princ "\nComando carregado: DrawGeneratedPipe")
