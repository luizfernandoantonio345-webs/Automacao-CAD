(defun c:DrawGeneratedPipe ()
  (setq layer_name "ENG_AUTO-0985")
  (command "_.-LAYER" "_Make" layer_name "")
  (setvar "CLAYER" layer_name)
  (command "_.LINE" "0.000,0.000" "1870.000,0.000" "")
  (command "_.CIRCLE" "0.000,0.000" "181.25")
  (command "_.ARC" "1870.000,0.000" "1870.000,362.500" "2232.500,362.500")
  (command "_.TEXT" "2252.500,-20.000" "5.0" "0" "EMPRESA: Engenharia CAD Labs")
  (command "_.TEXT" "2252.500,-28.000" "5.0" "0" "PECA: Curva")
  (command "_.TEXT" "2252.500,-36.000" "5.0" "0" "CODIGO: AUTO-0985")
  (princ "\nProjeto gerado com sucesso.")
)
(princ "\nComando carregado: DrawGeneratedPipe")
