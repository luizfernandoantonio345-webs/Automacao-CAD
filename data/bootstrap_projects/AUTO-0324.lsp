(defun c:DrawGeneratedPipe ()
  (setq layer_name "ENG_AUTO-0324")
  (command "_.-LAYER" "_Make" layer_name "")
  (setvar "CLAYER" layer_name)
  (command "_.LINE" "0.000,0.000" "1835.000,0.000" "")
  (command "_.CIRCLE" "0.000,0.000" "50.0")
  (command "_.ARC" "1835.000,0.000" "1835.000,100.000" "1935.000,100.000")
  (command "_.TEXT" "1955.000,-20.000" "5.0" "0" "EMPRESA: Atlas Engenharia")
  (command "_.TEXT" "1955.000,-28.000" "5.0" "0" "PECA: Tubo")
  (command "_.TEXT" "1955.000,-36.000" "5.0" "0" "CODIGO: AUTO-0324")
  (princ "\nProjeto gerado com sucesso.")
)
(princ "\nComando carregado: DrawGeneratedPipe")
