(defun c:DrawGeneratedPipe ()
  (setq layer_name "ENG_AUTO-0812")
  (command "_.-LAYER" "_Make" layer_name "")
  (setvar "CLAYER" layer_name)
  (command "_.LINE" "0.000,0.000" "1590.000,0.000" "")
  (command "_.CIRCLE" "0.000,0.000" "100.0")
  (command "_.ARC" "1590.000,0.000" "1590.000,200.000" "1790.000,200.000")
  (command "_.TEXT" "1810.000,-20.000" "5.0" "0" "EMPRESA: Norte Tubulacoes")
  (command "_.TEXT" "1810.000,-28.000" "5.0" "0" "PECA: Tee")
  (command "_.TEXT" "1810.000,-36.000" "5.0" "0" "CODIGO: AUTO-0812")
  (princ "\nProjeto gerado com sucesso.")
)
(princ "\nComando carregado: DrawGeneratedPipe")
