(defun c:DrawGeneratedPipe ()
  (setq layer_name "ENG_AUTO-0611")
  (command "_.-LAYER" "_Make" layer_name "")
  (setvar "CLAYER" layer_name)
  (command "_.LINE" "0.000,0.000" "330.000,0.000" "")
  (command "_.CIRCLE" "0.000,0.000" "93.75")
  (command "_.ARC" "330.000,0.000" "330.000,187.500" "517.500,187.500")
  (command "_.TEXT" "537.500,-20.000" "5.0" "0" "EMPRESA: Omega Piping")
  (command "_.TEXT" "537.500,-28.000" "5.0" "0" "PECA: Valve")
  (command "_.TEXT" "537.500,-36.000" "5.0" "0" "CODIGO: AUTO-0611")
  (princ "\nProjeto gerado com sucesso.")
)
(princ "\nComando carregado: DrawGeneratedPipe")
