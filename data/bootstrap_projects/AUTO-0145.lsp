(defun c:DrawGeneratedPipe ()
  (setq layer_name "ENG_AUTO-0145")
  (command "_.-LAYER" "_Make" layer_name "")
  (setvar "CLAYER" layer_name)
  (command "_.LINE" "0.000,0.000" "1345.000,0.000" "")
  (command "_.CIRCLE" "0.000,0.000" "181.25")
  (command "_.ARC" "1345.000,0.000" "1345.000,362.500" "1707.500,362.500")
  (command "_.TEXT" "1727.500,-20.000" "5.0" "0" "EMPRESA: Engenharia CAD Labs")
  (command "_.TEXT" "1727.500,-28.000" "5.0" "0" "PECA: Curva")
  (command "_.TEXT" "1727.500,-36.000" "5.0" "0" "CODIGO: AUTO-0145")
  (princ "\nProjeto gerado com sucesso.")
)
(princ "\nComando carregado: DrawGeneratedPipe")
