(defun c:DrawGeneratedPipe ()
  (setq layer_name "ENG_AUTO-1015")
  (command "_.-LAYER" "_Make" layer_name "")
  (setvar "CLAYER" layer_name)
  (command "_.LINE" "0.000,0.000" "995.000,0.000" "")
  (command "_.CIRCLE" "0.000,0.000" "118.75")
  (command "_.ARC" "995.000,0.000" "995.000,237.500" "1232.500,237.500")
  (command "_.TEXT" "1252.500,-20.000" "5.0" "0" "EMPRESA: Engenharia CAD Labs")
  (command "_.TEXT" "1252.500,-28.000" "5.0" "0" "PECA: Curva")
  (command "_.TEXT" "1252.500,-36.000" "5.0" "0" "CODIGO: AUTO-1015")
  (princ "\nProjeto gerado com sucesso.")
)
(princ "\nComando carregado: DrawGeneratedPipe")
