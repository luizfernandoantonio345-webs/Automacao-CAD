(defun c:DrawGeneratedPipe ()
  (setq layer_name "ENG_AUTO-0718")
  (command "_.-LAYER" "_Make" layer_name "")
  (setvar "CLAYER" layer_name)
  (command "_.LINE" "0.000,0.000" "225.000,0.000" "")
  (command "_.CIRCLE" "0.000,0.000" "262.5")
  (command "_.ARC" "225.000,0.000" "225.000,525.000" "750.000,525.000")
  (command "_.TEXT" "770.000,-20.000" "5.0" "0" "EMPRESA: Montreal Plantas")
  (command "_.TEXT" "770.000,-28.000" "5.0" "0" "PECA: Reducer")
  (command "_.TEXT" "770.000,-36.000" "5.0" "0" "CODIGO: AUTO-0718")
  (princ "\nProjeto gerado com sucesso.")
)
(princ "\nComando carregado: DrawGeneratedPipe")
