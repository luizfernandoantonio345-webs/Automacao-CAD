(defun c:DrawGeneratedPipe ()
  (setq layer_name "ENG_AUTO-0441")
  (command "_.-LAYER" "_Make" layer_name "")
  (setvar "CLAYER" layer_name)
  (command "_.LINE" "0.000,0.000" "155.000,0.000" "")
  (command "_.CIRCLE" "0.000,0.000" "31.25")
  (command "_.ARC" "155.000,0.000" "155.000,62.500" "217.500,62.500")
  (command "_.TEXT" "237.500,-20.000" "5.0" "0" "EMPRESA: Sul Processos")
  (command "_.TEXT" "237.500,-28.000" "5.0" "0" "PECA: Flange")
  (command "_.TEXT" "237.500,-36.000" "5.0" "0" "CODIGO: AUTO-0441")
  (princ "\nProjeto gerado com sucesso.")
)
(princ "\nComando carregado: DrawGeneratedPipe")
