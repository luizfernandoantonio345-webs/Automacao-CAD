(defun c:DrawGeneratedPipe ()
  (setq layer_name "ENG_AUTO-0231")
  (command "_.-LAYER" "_Make" layer_name "")
  (setvar "CLAYER" layer_name)
  (command "_.LINE" "0.000,0.000" "505.000,0.000" "")
  (command "_.CIRCLE" "0.000,0.000" "218.75")
  (command "_.ARC" "505.000,0.000" "505.000,437.500" "942.500,437.500")
  (command "_.TEXT" "962.500,-20.000" "5.0" "0" "EMPRESA: Sul Processos")
  (command "_.TEXT" "962.500,-28.000" "5.0" "0" "PECA: Flange")
  (command "_.TEXT" "962.500,-36.000" "5.0" "0" "CODIGO: AUTO-0231")
  (princ "\nProjeto gerado com sucesso.")
)
(princ "\nComando carregado: DrawGeneratedPipe")
