(defun c:DrawGeneratedPipe ()
  (setq layer_name "ENG_AUTO-0247")
  (command "_.-LAYER" "_Make" layer_name "")
  (setvar "CLAYER" layer_name)
  (command "_.LINE" "0.000,0.000" "1065.000,0.000" "")
  (command "_.CIRCLE" "0.000,0.000" "68.75")
  (command "_.ARC" "1065.000,0.000" "1065.000,137.500" "1202.500,137.500")
  (command "_.TEXT" "1222.500,-20.000" "5.0" "0" "EMPRESA: Engenharia CAD Labs")
  (command "_.TEXT" "1222.500,-28.000" "5.0" "0" "PECA: Curva")
  (command "_.TEXT" "1222.500,-36.000" "5.0" "0" "CODIGO: AUTO-0247")
  (princ "\nProjeto gerado com sucesso.")
)
(princ "\nComando carregado: DrawGeneratedPipe")
