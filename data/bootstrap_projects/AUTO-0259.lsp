(defun c:DrawGeneratedPipe ()
  (setq layer_name "ENG_AUTO-0259")
  (command "_.-LAYER" "_Make" layer_name "")
  (setvar "CLAYER" layer_name)
  (command "_.LINE" "0.000,0.000" "1485.000,0.000" "")
  (command "_.CIRCLE" "0.000,0.000" "143.75")
  (command "_.ARC" "1485.000,0.000" "1485.000,287.500" "1772.500,287.500")
  (command "_.TEXT" "1792.500,-20.000" "5.0" "0" "EMPRESA: Engenharia CAD Labs")
  (command "_.TEXT" "1792.500,-28.000" "5.0" "0" "PECA: Curva")
  (command "_.TEXT" "1792.500,-36.000" "5.0" "0" "CODIGO: AUTO-0259")
  (princ "\nProjeto gerado com sucesso.")
)
(princ "\nComando carregado: DrawGeneratedPipe")
