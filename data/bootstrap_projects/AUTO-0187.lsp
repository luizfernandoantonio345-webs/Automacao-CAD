(defun c:DrawGeneratedPipe ()
  (setq layer_name "ENG_AUTO-0187")
  (command "_.-LAYER" "_Make" layer_name "")
  (setvar "CLAYER" layer_name)
  (command "_.LINE" "0.000,0.000" "890.000,0.000" "")
  (command "_.CIRCLE" "0.000,0.000" "193.75")
  (command "_.ARC" "890.000,0.000" "890.000,387.500" "1277.500,387.500")
  (command "_.TEXT" "1297.500,-20.000" "5.0" "0" "EMPRESA: Engenharia CAD Labs")
  (command "_.TEXT" "1297.500,-28.000" "5.0" "0" "PECA: Curva")
  (command "_.TEXT" "1297.500,-36.000" "5.0" "0" "CODIGO: AUTO-0187")
  (princ "\nProjeto gerado com sucesso.")
)
(princ "\nComando carregado: DrawGeneratedPipe")
