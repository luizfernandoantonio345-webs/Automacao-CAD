(defun c:DrawGeneratedPipe ()
  (setq layer_name "ENG_AUTO-0957")
  (command "_.-LAYER" "_Make" layer_name "")
  (setvar "CLAYER" layer_name)
  (command "_.LINE" "0.000,0.000" "890.000,0.000" "")
  (command "_.CIRCLE" "0.000,0.000" "256.25")
  (command "_.ARC" "890.000,0.000" "890.000,512.500" "1402.500,512.500")
  (command "_.TEXT" "1422.500,-20.000" "5.0" "0" "EMPRESA: Sul Processos")
  (command "_.TEXT" "1422.500,-28.000" "5.0" "0" "PECA: Flange")
  (command "_.TEXT" "1422.500,-36.000" "5.0" "0" "CODIGO: AUTO-0957")
  (princ "\nProjeto gerado com sucesso.")
)
(princ "\nComando carregado: DrawGeneratedPipe")
