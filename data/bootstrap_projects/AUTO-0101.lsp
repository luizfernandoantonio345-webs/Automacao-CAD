(defun c:DrawGeneratedPipe ()
  (setq layer_name "ENG_AUTO-0101")
  (command "_.-LAYER" "_Make" layer_name "")
  (setvar "CLAYER" layer_name)
  (command "_.LINE" "0.000,0.000" "1730.000,0.000" "")
  (command "_.CIRCLE" "0.000,0.000" "156.25")
  (command "_.ARC" "1730.000,0.000" "1730.000,312.500" "2042.500,312.500")
  (command "_.TEXT" "2062.500,-20.000" "5.0" "0" "EMPRESA: Omega Piping")
  (command "_.TEXT" "2062.500,-28.000" "5.0" "0" "PECA: Valve")
  (command "_.TEXT" "2062.500,-36.000" "5.0" "0" "CODIGO: AUTO-0101")
  (princ "\nProjeto gerado com sucesso.")
)
(princ "\nComando carregado: DrawGeneratedPipe")
