(defun c:DrawGeneratedPipe ()
  (setq layer_name "ENG_AUTO-0591")
  (command "_.-LAYER" "_Make" layer_name "")
  (setvar "CLAYER" layer_name)
  (command "_.LINE" "0.000,0.000" "1555.000,0.000" "")
  (command "_.CIRCLE" "0.000,0.000" "218.75")
  (command "_.ARC" "1555.000,0.000" "1555.000,437.500" "1992.500,437.500")
  (command "_.TEXT" "2012.500,-20.000" "5.0" "0" "EMPRESA: Sul Processos")
  (command "_.TEXT" "2012.500,-28.000" "5.0" "0" "PECA: Flange")
  (command "_.TEXT" "2012.500,-36.000" "5.0" "0" "CODIGO: AUTO-0591")
  (princ "\nProjeto gerado com sucesso.")
)
(princ "\nComando carregado: DrawGeneratedPipe")
