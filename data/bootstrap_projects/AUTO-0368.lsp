(defun c:DrawGeneratedPipe ()
  (setq layer_name "ENG_AUTO-0368")
  (command "_.-LAYER" "_Make" layer_name "")
  (setvar "CLAYER" layer_name)
  (command "_.LINE" "0.000,0.000" "1450.000,0.000" "")
  (command "_.CIRCLE" "0.000,0.000" "75.0")
  (command "_.ARC" "1450.000,0.000" "1450.000,150.000" "1600.000,150.000")
  (command "_.TEXT" "1620.000,-20.000" "5.0" "0" "EMPRESA: Norte Tubulacoes")
  (command "_.TEXT" "1620.000,-28.000" "5.0" "0" "PECA: Tee")
  (command "_.TEXT" "1620.000,-36.000" "5.0" "0" "CODIGO: AUTO-0368")
  (princ "\nProjeto gerado com sucesso.")
)
(princ "\nComando carregado: DrawGeneratedPipe")
