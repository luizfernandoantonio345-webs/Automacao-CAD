(defun c:DrawGeneratedPipe ()
  (setq layer_name "ENG_AUTO-1101")
  (command "_.-LAYER" "_Make" layer_name "")
  (setvar "CLAYER" layer_name)
  (command "_.LINE" "0.000,0.000" "155.000,0.000" "")
  (command "_.CIRCLE" "0.000,0.000" "156.25")
  (command "_.ARC" "155.000,0.000" "155.000,312.500" "467.500,312.500")
  (command "_.TEXT" "487.500,-20.000" "5.0" "0" "EMPRESA: Sul Processos")
  (command "_.TEXT" "487.500,-28.000" "5.0" "0" "PECA: Flange")
  (command "_.TEXT" "487.500,-36.000" "5.0" "0" "CODIGO: AUTO-1101")
  (princ "\nProjeto gerado com sucesso.")
)
(princ "\nComando carregado: DrawGeneratedPipe")
