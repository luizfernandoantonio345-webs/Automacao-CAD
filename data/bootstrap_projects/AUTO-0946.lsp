(defun c:DrawGeneratedPipe ()
  (setq layer_name "ENG_AUTO-0946")
  (command "_.-LAYER" "_Make" layer_name "")
  (setvar "CLAYER" layer_name)
  (command "_.LINE" "0.000,0.000" "505.000,0.000" "")
  (command "_.CIRCLE" "0.000,0.000" "187.5")
  (command "_.ARC" "505.000,0.000" "505.000,375.000" "880.000,375.000")
  (command "_.TEXT" "900.000,-20.000" "5.0" "0" "EMPRESA: Montreal Plantas")
  (command "_.TEXT" "900.000,-28.000" "5.0" "0" "PECA: Reducer")
  (command "_.TEXT" "900.000,-36.000" "5.0" "0" "CODIGO: AUTO-0946")
  (princ "\nProjeto gerado com sucesso.")
)
(princ "\nComando carregado: DrawGeneratedPipe")
