(defun c:DrawGeneratedPipe ()
  (setq layer_name "ENG_AUTO-0354")
  (command "_.-LAYER" "_Make" layer_name "")
  (setvar "CLAYER" layer_name)
  (command "_.LINE" "0.000,0.000" "960.000,0.000" "")
  (command "_.CIRCLE" "0.000,0.000" "237.5")
  (command "_.ARC" "960.000,0.000" "960.000,475.000" "1435.000,475.000")
  (command "_.TEXT" "1455.000,-20.000" "5.0" "0" "EMPRESA: Atlas Engenharia")
  (command "_.TEXT" "1455.000,-28.000" "5.0" "0" "PECA: Tubo")
  (command "_.TEXT" "1455.000,-36.000" "5.0" "0" "CODIGO: AUTO-0354")
  (princ "\nProjeto gerado com sucesso.")
)
(princ "\nComando carregado: DrawGeneratedPipe")
