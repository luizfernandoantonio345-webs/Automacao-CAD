(defun c:DrawGeneratedPipe ()
  (setq layer_name "ENG_AUTO-0333")
  (command "_.-LAYER" "_Make" layer_name "")
  (setvar "CLAYER" layer_name)
  (command "_.LINE" "0.000,0.000" "225.000,0.000" "")
  (command "_.CIRCLE" "0.000,0.000" "106.25")
  (command "_.ARC" "225.000,0.000" "225.000,212.500" "437.500,212.500")
  (command "_.TEXT" "457.500,-20.000" "5.0" "0" "EMPRESA: Sul Processos")
  (command "_.TEXT" "457.500,-28.000" "5.0" "0" "PECA: Flange")
  (command "_.TEXT" "457.500,-36.000" "5.0" "0" "CODIGO: AUTO-0333")
  (princ "\nProjeto gerado com sucesso.")
)
(princ "\nComando carregado: DrawGeneratedPipe")
