(defun c:DrawGeneratedPipe ()
  (setq layer_name "ENG_AUTO-0907")
  (command "_.-LAYER" "_Make" layer_name "")
  (setvar "CLAYER" layer_name)
  (command "_.LINE" "0.000,0.000" "1065.000,0.000" "")
  (command "_.CIRCLE" "0.000,0.000" "193.75")
  (command "_.ARC" "1065.000,0.000" "1065.000,387.500" "1452.500,387.500")
  (command "_.TEXT" "1472.500,-20.000" "5.0" "0" "EMPRESA: Engenharia CAD Labs")
  (command "_.TEXT" "1472.500,-28.000" "5.0" "0" "PECA: Curva")
  (command "_.TEXT" "1472.500,-36.000" "5.0" "0" "CODIGO: AUTO-0907")
  (princ "\nProjeto gerado com sucesso.")
)
(princ "\nComando carregado: DrawGeneratedPipe")
