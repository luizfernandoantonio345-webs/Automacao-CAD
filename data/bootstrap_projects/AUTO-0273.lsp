(defun c:DrawGeneratedPipe ()
  (setq layer_name "ENG_AUTO-0273")
  (command "_.-LAYER" "_Make" layer_name "")
  (setvar "CLAYER" layer_name)
  (command "_.LINE" "0.000,0.000" "1975.000,0.000" "")
  (command "_.CIRCLE" "0.000,0.000" "231.25")
  (command "_.ARC" "1975.000,0.000" "1975.000,462.500" "2437.500,462.500")
  (command "_.TEXT" "2457.500,-20.000" "5.0" "0" "EMPRESA: Sul Processos")
  (command "_.TEXT" "2457.500,-28.000" "5.0" "0" "PECA: Flange")
  (command "_.TEXT" "2457.500,-36.000" "5.0" "0" "CODIGO: AUTO-0273")
  (princ "\nProjeto gerado com sucesso.")
)
(princ "\nComando carregado: DrawGeneratedPipe")
