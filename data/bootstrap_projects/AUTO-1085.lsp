(defun c:DrawGeneratedPipe ()
  (setq layer_name "ENG_AUTO-1085")
  (command "_.-LAYER" "_Make" layer_name "")
  (setvar "CLAYER" layer_name)
  (command "_.LINE" "0.000,0.000" "1520.000,0.000" "")
  (command "_.CIRCLE" "0.000,0.000" "56.25")
  (command "_.ARC" "1520.000,0.000" "1520.000,112.500" "1632.500,112.500")
  (command "_.TEXT" "1652.500,-20.000" "5.0" "0" "EMPRESA: Omega Piping")
  (command "_.TEXT" "1652.500,-28.000" "5.0" "0" "PECA: Valve")
  (command "_.TEXT" "1652.500,-36.000" "5.0" "0" "CODIGO: AUTO-1085")
  (princ "\nProjeto gerado com sucesso.")
)
(princ "\nComando carregado: DrawGeneratedPipe")
