(defun c:DrawGeneratedPipe ()
  (setq layer_name "ENG_AUTO-1117")
  (command "_.-LAYER" "_Make" layer_name "")
  (setvar "CLAYER" layer_name)
  (command "_.LINE" "0.000,0.000" "715.000,0.000" "")
  (command "_.CIRCLE" "0.000,0.000" "256.25")
  (command "_.ARC" "715.000,0.000" "715.000,512.500" "1227.500,512.500")
  (command "_.TEXT" "1247.500,-20.000" "5.0" "0" "EMPRESA: Engenharia CAD Labs")
  (command "_.TEXT" "1247.500,-28.000" "5.0" "0" "PECA: Curva")
  (command "_.TEXT" "1247.500,-36.000" "5.0" "0" "CODIGO: AUTO-1117")
  (princ "\nProjeto gerado com sucesso.")
)
(princ "\nComando carregado: DrawGeneratedPipe")
