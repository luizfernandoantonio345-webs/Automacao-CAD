(defun c:DrawGeneratedPipe ()
  (setq layer_name "ENG_AUTO-1016")
  (command "_.-LAYER" "_Make" layer_name "")
  (setvar "CLAYER" layer_name)
  (command "_.LINE" "0.000,0.000" "1030.000,0.000" "")
  (command "_.CIRCLE" "0.000,0.000" "125.0")
  (command "_.ARC" "1030.000,0.000" "1030.000,250.000" "1280.000,250.000")
  (command "_.TEXT" "1300.000,-20.000" "5.0" "0" "EMPRESA: Norte Tubulacoes")
  (command "_.TEXT" "1300.000,-28.000" "5.0" "0" "PECA: Tee")
  (command "_.TEXT" "1300.000,-36.000" "5.0" "0" "CODIGO: AUTO-1016")
  (princ "\nProjeto gerado com sucesso.")
)
(princ "\nComando carregado: DrawGeneratedPipe")
