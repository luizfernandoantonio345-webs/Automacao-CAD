(defun c:DrawGeneratedPipe ()
  (setq layer_name "ENG_AUTO-0138")
  (command "_.-LAYER" "_Make" layer_name "")
  (setvar "CLAYER" layer_name)
  (command "_.LINE" "0.000,0.000" "1100.000,0.000" "")
  (command "_.CIRCLE" "0.000,0.000" "137.5")
  (command "_.ARC" "1100.000,0.000" "1100.000,275.000" "1375.000,275.000")
  (command "_.TEXT" "1395.000,-20.000" "5.0" "0" "EMPRESA: Atlas Engenharia")
  (command "_.TEXT" "1395.000,-28.000" "5.0" "0" "PECA: Tubo")
  (command "_.TEXT" "1395.000,-36.000" "5.0" "0" "CODIGO: AUTO-0138")
  (princ "\nProjeto gerado com sucesso.")
)
(princ "\nComando carregado: DrawGeneratedPipe")
