(defun c:DrawGeneratedPipe ()
  (setq layer_name "ENG_AUTO-0963")
  (command "_.-LAYER" "_Make" layer_name "")
  (setvar "CLAYER" layer_name)
  (command "_.LINE" "0.000,0.000" "1100.000,0.000" "")
  (command "_.CIRCLE" "0.000,0.000" "43.75")
  (command "_.ARC" "1100.000,0.000" "1100.000,87.500" "1187.500,87.500")
  (command "_.TEXT" "1207.500,-20.000" "5.0" "0" "EMPRESA: Sul Processos")
  (command "_.TEXT" "1207.500,-28.000" "5.0" "0" "PECA: Flange")
  (command "_.TEXT" "1207.500,-36.000" "5.0" "0" "CODIGO: AUTO-0963")
  (princ "\nProjeto gerado com sucesso.")
)
(princ "\nComando carregado: DrawGeneratedPipe")
