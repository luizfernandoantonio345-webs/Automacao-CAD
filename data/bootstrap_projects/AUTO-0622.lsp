(defun c:DrawGeneratedPipe ()
  (setq layer_name "ENG_AUTO-0622")
  (command "_.-LAYER" "_Make" layer_name "")
  (setvar "CLAYER" layer_name)
  (command "_.LINE" "0.000,0.000" "715.000,0.000" "")
  (command "_.CIRCLE" "0.000,0.000" "162.5")
  (command "_.ARC" "715.000,0.000" "715.000,325.000" "1040.000,325.000")
  (command "_.TEXT" "1060.000,-20.000" "5.0" "0" "EMPRESA: Montreal Plantas")
  (command "_.TEXT" "1060.000,-28.000" "5.0" "0" "PECA: Reducer")
  (command "_.TEXT" "1060.000,-36.000" "5.0" "0" "CODIGO: AUTO-0622")
  (princ "\nProjeto gerado com sucesso.")
)
(princ "\nComando carregado: DrawGeneratedPipe")
