(defun c:DrawGeneratedPipe ()
  (setq layer_name "ENG_AUTO-1070")
  (command "_.-LAYER" "_Make" layer_name "")
  (setvar "CLAYER" layer_name)
  (command "_.LINE" "0.000,0.000" "995.000,0.000" "")
  (command "_.CIRCLE" "0.000,0.000" "212.5")
  (command "_.ARC" "995.000,0.000" "995.000,425.000" "1420.000,425.000")
  (command "_.TEXT" "1440.000,-20.000" "5.0" "0" "EMPRESA: Norte Tubulacoes")
  (command "_.TEXT" "1440.000,-28.000" "5.0" "0" "PECA: Tee")
  (command "_.TEXT" "1440.000,-36.000" "5.0" "0" "CODIGO: AUTO-1070")
  (princ "\nProjeto gerado com sucesso.")
)
(princ "\nComando carregado: DrawGeneratedPipe")
