(defun c:DrawGeneratedPipe ()
  (setq layer_name "ENG_AUTO-0897")
  (command "_.-LAYER" "_Make" layer_name "")
  (setvar "CLAYER" layer_name)
  (command "_.LINE" "0.000,0.000" "715.000,0.000" "")
  (command "_.CIRCLE" "0.000,0.000" "131.25")
  (command "_.ARC" "715.000,0.000" "715.000,262.500" "977.500,262.500")
  (command "_.TEXT" "997.500,-20.000" "5.0" "0" "EMPRESA: Sul Processos")
  (command "_.TEXT" "997.500,-28.000" "5.0" "0" "PECA: Flange")
  (command "_.TEXT" "997.500,-36.000" "5.0" "0" "CODIGO: AUTO-0897")
  (princ "\nProjeto gerado com sucesso.")
)
(princ "\nComando carregado: DrawGeneratedPipe")
