(defun c:DrawGeneratedPipe ()
  (setq layer_name "ENG_AUTO-0728")
  (command "_.-LAYER" "_Make" layer_name "")
  (setvar "CLAYER" layer_name)
  (command "_.LINE" "0.000,0.000" "575.000,0.000" "")
  (command "_.CIRCLE" "0.000,0.000" "75.0")
  (command "_.ARC" "575.000,0.000" "575.000,150.000" "725.000,150.000")
  (command "_.TEXT" "745.000,-20.000" "5.0" "0" "EMPRESA: Norte Tubulacoes")
  (command "_.TEXT" "745.000,-28.000" "5.0" "0" "PECA: Tee")
  (command "_.TEXT" "745.000,-36.000" "5.0" "0" "CODIGO: AUTO-0728")
  (princ "\nProjeto gerado com sucesso.")
)
(princ "\nComando carregado: DrawGeneratedPipe")
