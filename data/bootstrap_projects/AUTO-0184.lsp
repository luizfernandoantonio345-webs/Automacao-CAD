(defun c:DrawGeneratedPipe ()
  (setq layer_name "ENG_AUTO-0184")
  (command "_.-LAYER" "_Make" layer_name "")
  (setvar "CLAYER" layer_name)
  (command "_.LINE" "0.000,0.000" "785.000,0.000" "")
  (command "_.CIRCLE" "0.000,0.000" "175.0")
  (command "_.ARC" "785.000,0.000" "785.000,350.000" "1135.000,350.000")
  (command "_.TEXT" "1155.000,-20.000" "5.0" "0" "EMPRESA: Montreal Plantas")
  (command "_.TEXT" "1155.000,-28.000" "5.0" "0" "PECA: Reducer")
  (command "_.TEXT" "1155.000,-36.000" "5.0" "0" "CODIGO: AUTO-0184")
  (princ "\nProjeto gerado com sucesso.")
)
(princ "\nComando carregado: DrawGeneratedPipe")
