(defun c:DrawGeneratedPipe ()
  (setq layer_name "ENG_AUTO-1035")
  (command "_.-LAYER" "_Make" layer_name "")
  (setvar "CLAYER" layer_name)
  (command "_.LINE" "0.000,0.000" "1695.000,0.000" "")
  (command "_.CIRCLE" "0.000,0.000" "243.75")
  (command "_.ARC" "1695.000,0.000" "1695.000,487.500" "2182.500,487.500")
  (command "_.TEXT" "2202.500,-20.000" "5.0" "0" "EMPRESA: Sul Processos")
  (command "_.TEXT" "2202.500,-28.000" "5.0" "0" "PECA: Flange")
  (command "_.TEXT" "2202.500,-36.000" "5.0" "0" "CODIGO: AUTO-1035")
  (princ "\nProjeto gerado com sucesso.")
)
(princ "\nComando carregado: DrawGeneratedPipe")
