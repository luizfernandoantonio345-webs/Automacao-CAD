(defun c:DrawGeneratedPipe ()
  (setq layer_name "ENG_AUTO-0931")
  (command "_.-LAYER" "_Make" layer_name "")
  (setvar "CLAYER" layer_name)
  (command "_.LINE" "0.000,0.000" "1905.000,0.000" "")
  (command "_.CIRCLE" "0.000,0.000" "93.75")
  (command "_.ARC" "1905.000,0.000" "1905.000,187.500" "2092.500,187.500")
  (command "_.TEXT" "2112.500,-20.000" "5.0" "0" "EMPRESA: Engenharia CAD Labs")
  (command "_.TEXT" "2112.500,-28.000" "5.0" "0" "PECA: Curva")
  (command "_.TEXT" "2112.500,-36.000" "5.0" "0" "CODIGO: AUTO-0931")
  (princ "\nProjeto gerado com sucesso.")
)
(princ "\nComando carregado: DrawGeneratedPipe")
