(defun c:DrawGeneratedPipe ()
  (setq layer_name "ENG_AUTO-0004")
  (command "_.-LAYER" "_Make" layer_name "")
  (setvar "CLAYER" layer_name)
  (command "_.LINE" "0.000,0.000" "260.000,0.000" "")
  (command "_.CIRCLE" "0.000,0.000" "50.0")
  (command "_.ARC" "260.000,0.000" "260.000,100.000" "360.000,100.000")
  (command "_.TEXT" "380.000,-20.000" "5.0" "0" "EMPRESA: Montreal Plantas")
  (command "_.TEXT" "380.000,-28.000" "5.0" "0" "PECA: Reducer")
  (command "_.TEXT" "380.000,-36.000" "5.0" "0" "CODIGO: AUTO-0004")
  (princ "\nProjeto gerado com sucesso.")
)
(princ "\nComando carregado: DrawGeneratedPipe")
