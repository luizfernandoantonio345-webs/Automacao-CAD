(defun c:DrawGeneratedPipe ()
  (setq layer_name "ENG_AUTO-1052")
  (command "_.-LAYER" "_Make" layer_name "")
  (setvar "CLAYER" layer_name)
  (command "_.LINE" "0.000,0.000" "365.000,0.000" "")
  (command "_.CIRCLE" "0.000,0.000" "100.0")
  (command "_.ARC" "365.000,0.000" "365.000,200.000" "565.000,200.000")
  (command "_.TEXT" "585.000,-20.000" "5.0" "0" "EMPRESA: Norte Tubulacoes")
  (command "_.TEXT" "585.000,-28.000" "5.0" "0" "PECA: Tee")
  (command "_.TEXT" "585.000,-36.000" "5.0" "0" "CODIGO: AUTO-1052")
  (princ "\nProjeto gerado com sucesso.")
)
(princ "\nComando carregado: DrawGeneratedPipe")
