(defun c:DrawGeneratedPipe ()
  (setq layer_name "ENG_AUTO-0159")
  (command "_.-LAYER" "_Make" layer_name "")
  (setvar "CLAYER" layer_name)
  (command "_.LINE" "0.000,0.000" "1835.000,0.000" "")
  (command "_.CIRCLE" "0.000,0.000" "268.75")
  (command "_.ARC" "1835.000,0.000" "1835.000,537.500" "2372.500,537.500")
  (command "_.TEXT" "2392.500,-20.000" "5.0" "0" "EMPRESA: Sul Processos")
  (command "_.TEXT" "2392.500,-28.000" "5.0" "0" "PECA: Flange")
  (command "_.TEXT" "2392.500,-36.000" "5.0" "0" "CODIGO: AUTO-0159")
  (princ "\nProjeto gerado com sucesso.")
)
(princ "\nComando carregado: DrawGeneratedPipe")
