(defun c:DrawGeneratedPipe ()
  (setq layer_name "ENG_AUTO-0189")
  (command "_.-LAYER" "_Make" layer_name "")
  (setvar "CLAYER" layer_name)
  (command "_.LINE" "0.000,0.000" "960.000,0.000" "")
  (command "_.CIRCLE" "0.000,0.000" "206.25")
  (command "_.ARC" "960.000,0.000" "960.000,412.500" "1372.500,412.500")
  (command "_.TEXT" "1392.500,-20.000" "5.0" "0" "EMPRESA: Sul Processos")
  (command "_.TEXT" "1392.500,-28.000" "5.0" "0" "PECA: Flange")
  (command "_.TEXT" "1392.500,-36.000" "5.0" "0" "CODIGO: AUTO-0189")
  (princ "\nProjeto gerado com sucesso.")
)
(princ "\nComando carregado: DrawGeneratedPipe")
