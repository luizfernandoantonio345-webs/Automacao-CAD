(defun c:DrawGeneratedPipe ()
  (setq layer_name "ENG_AUTO-1114")
  (command "_.-LAYER" "_Make" layer_name "")
  (setvar "CLAYER" layer_name)
  (command "_.LINE" "0.000,0.000" "610.000,0.000" "")
  (command "_.CIRCLE" "0.000,0.000" "237.5")
  (command "_.ARC" "610.000,0.000" "610.000,475.000" "1085.000,475.000")
  (command "_.TEXT" "1105.000,-20.000" "5.0" "0" "EMPRESA: Montreal Plantas")
  (command "_.TEXT" "1105.000,-28.000" "5.0" "0" "PECA: Reducer")
  (command "_.TEXT" "1105.000,-36.000" "5.0" "0" "CODIGO: AUTO-1114")
  (princ "\nProjeto gerado com sucesso.")
)
(princ "\nComando carregado: DrawGeneratedPipe")
