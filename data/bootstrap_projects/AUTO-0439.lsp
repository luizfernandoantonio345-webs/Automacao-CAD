(defun c:DrawGeneratedPipe ()
  (setq layer_name "ENG_AUTO-0439")
  (command "_.-LAYER" "_Make" layer_name "")
  (setvar "CLAYER" layer_name)
  (command "_.LINE" "0.000,0.000" "2010.000,0.000" "")
  (command "_.CIRCLE" "0.000,0.000" "268.75")
  (command "_.ARC" "2010.000,0.000" "2010.000,537.500" "2547.500,537.500")
  (command "_.TEXT" "2567.500,-20.000" "5.0" "0" "EMPRESA: Engenharia CAD Labs")
  (command "_.TEXT" "2567.500,-28.000" "5.0" "0" "PECA: Curva")
  (command "_.TEXT" "2567.500,-36.000" "5.0" "0" "CODIGO: AUTO-0439")
  (princ "\nProjeto gerado com sucesso.")
)
(princ "\nComando carregado: DrawGeneratedPipe")
