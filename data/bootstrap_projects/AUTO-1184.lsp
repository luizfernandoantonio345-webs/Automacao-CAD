(defun c:DrawGeneratedPipe ()
  (setq layer_name "ENG_AUTO-1184")
  (command "_.-LAYER" "_Make" layer_name "")
  (setvar "CLAYER" layer_name)
  (command "_.LINE" "0.000,0.000" "1135.000,0.000" "")
  (command "_.CIRCLE" "0.000,0.000" "175.0")
  (command "_.ARC" "1135.000,0.000" "1135.000,350.000" "1485.000,350.000")
  (command "_.TEXT" "1505.000,-20.000" "5.0" "0" "EMPRESA: Norte Tubulacoes")
  (command "_.TEXT" "1505.000,-28.000" "5.0" "0" "PECA: Tee")
  (command "_.TEXT" "1505.000,-36.000" "5.0" "0" "CODIGO: AUTO-1184")
  (princ "\nProjeto gerado com sucesso.")
)
(princ "\nComando carregado: DrawGeneratedPipe")
