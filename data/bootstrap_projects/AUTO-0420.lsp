(defun c:DrawGeneratedPipe ()
  (setq layer_name "ENG_AUTO-0420")
  (command "_.-LAYER" "_Make" layer_name "")
  (setvar "CLAYER" layer_name)
  (command "_.LINE" "0.000,0.000" "1345.000,0.000" "")
  (command "_.CIRCLE" "0.000,0.000" "150.0")
  (command "_.ARC" "1345.000,0.000" "1345.000,300.000" "1645.000,300.000")
  (command "_.TEXT" "1665.000,-20.000" "5.0" "0" "EMPRESA: Atlas Engenharia")
  (command "_.TEXT" "1665.000,-28.000" "5.0" "0" "PECA: Tubo")
  (command "_.TEXT" "1665.000,-36.000" "5.0" "0" "CODIGO: AUTO-0420")
  (princ "\nProjeto gerado com sucesso.")
)
(princ "\nComando carregado: DrawGeneratedPipe")
