(defun c:DrawGeneratedPipe ()
  (setq layer_name "ENG_AUTO-0820")
  (command "_.-LAYER" "_Make" layer_name "")
  (setvar "CLAYER" layer_name)
  (command "_.LINE" "0.000,0.000" "1870.000,0.000" "")
  (command "_.CIRCLE" "0.000,0.000" "150.0")
  (command "_.ARC" "1870.000,0.000" "1870.000,300.000" "2170.000,300.000")
  (command "_.TEXT" "2190.000,-20.000" "5.0" "0" "EMPRESA: Montreal Plantas")
  (command "_.TEXT" "2190.000,-28.000" "5.0" "0" "PECA: Reducer")
  (command "_.TEXT" "2190.000,-36.000" "5.0" "0" "CODIGO: AUTO-0820")
  (princ "\nProjeto gerado com sucesso.")
)
(princ "\nComando carregado: DrawGeneratedPipe")
