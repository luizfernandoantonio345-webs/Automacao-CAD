(defun c:DrawGeneratedPipe ()
  (setq layer_name "ENG_AUTO-0976")
  (command "_.-LAYER" "_Make" layer_name "")
  (setvar "CLAYER" layer_name)
  (command "_.LINE" "0.000,0.000" "1555.000,0.000" "")
  (command "_.CIRCLE" "0.000,0.000" "125.0")
  (command "_.ARC" "1555.000,0.000" "1555.000,250.000" "1805.000,250.000")
  (command "_.TEXT" "1825.000,-20.000" "5.0" "0" "EMPRESA: Montreal Plantas")
  (command "_.TEXT" "1825.000,-28.000" "5.0" "0" "PECA: Reducer")
  (command "_.TEXT" "1825.000,-36.000" "5.0" "0" "CODIGO: AUTO-0976")
  (princ "\nProjeto gerado com sucesso.")
)
(princ "\nComando carregado: DrawGeneratedPipe")
