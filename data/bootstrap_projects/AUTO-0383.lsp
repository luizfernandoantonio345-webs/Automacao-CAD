(defun c:DrawGeneratedPipe ()
  (setq layer_name "ENG_AUTO-0383")
  (command "_.-LAYER" "_Make" layer_name "")
  (setvar "CLAYER" layer_name)
  (command "_.LINE" "0.000,0.000" "1975.000,0.000" "")
  (command "_.CIRCLE" "0.000,0.000" "168.75")
  (command "_.ARC" "1975.000,0.000" "1975.000,337.500" "2312.500,337.500")
  (command "_.TEXT" "2332.500,-20.000" "5.0" "0" "EMPRESA: Omega Piping")
  (command "_.TEXT" "2332.500,-28.000" "5.0" "0" "PECA: Valve")
  (command "_.TEXT" "2332.500,-36.000" "5.0" "0" "CODIGO: AUTO-0383")
  (princ "\nProjeto gerado com sucesso.")
)
(princ "\nComando carregado: DrawGeneratedPipe")
