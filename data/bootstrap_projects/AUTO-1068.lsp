(defun c:DrawGeneratedPipe ()
  (setq layer_name "ENG_AUTO-1068")
  (command "_.-LAYER" "_Make" layer_name "")
  (setvar "CLAYER" layer_name)
  (command "_.LINE" "0.000,0.000" "925.000,0.000" "")
  (command "_.CIRCLE" "0.000,0.000" "200.0")
  (command "_.ARC" "925.000,0.000" "925.000,400.000" "1325.000,400.000")
  (command "_.TEXT" "1345.000,-20.000" "5.0" "0" "EMPRESA: Atlas Engenharia")
  (command "_.TEXT" "1345.000,-28.000" "5.0" "0" "PECA: Tubo")
  (command "_.TEXT" "1345.000,-36.000" "5.0" "0" "CODIGO: AUTO-1068")
  (princ "\nProjeto gerado com sucesso.")
)
(princ "\nComando carregado: DrawGeneratedPipe")
