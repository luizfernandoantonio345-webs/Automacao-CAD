(defun c:DrawGeneratedPipe ()
  (setq layer_name "ENG_AUTO-0953")
  (command "_.-LAYER" "_Make" layer_name "")
  (setvar "CLAYER" layer_name)
  (command "_.LINE" "0.000,0.000" "750.000,0.000" "")
  (command "_.CIRCLE" "0.000,0.000" "231.25")
  (command "_.ARC" "750.000,0.000" "750.000,462.500" "1212.500,462.500")
  (command "_.TEXT" "1232.500,-20.000" "5.0" "0" "EMPRESA: Omega Piping")
  (command "_.TEXT" "1232.500,-28.000" "5.0" "0" "PECA: Valve")
  (command "_.TEXT" "1232.500,-36.000" "5.0" "0" "CODIGO: AUTO-0953")
  (princ "\nProjeto gerado com sucesso.")
)
(princ "\nComando carregado: DrawGeneratedPipe")
