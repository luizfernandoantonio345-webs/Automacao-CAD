(defun c:DrawGeneratedPipe ()
  (setq layer_name "ENG_AUTO-0191")
  (command "_.-LAYER" "_Make" layer_name "")
  (setvar "CLAYER" layer_name)
  (command "_.LINE" "0.000,0.000" "1030.000,0.000" "")
  (command "_.CIRCLE" "0.000,0.000" "218.75")
  (command "_.ARC" "1030.000,0.000" "1030.000,437.500" "1467.500,437.500")
  (command "_.TEXT" "1487.500,-20.000" "5.0" "0" "EMPRESA: Omega Piping")
  (command "_.TEXT" "1487.500,-28.000" "5.0" "0" "PECA: Valve")
  (command "_.TEXT" "1487.500,-36.000" "5.0" "0" "CODIGO: AUTO-0191")
  (princ "\nProjeto gerado com sucesso.")
)
(princ "\nComando carregado: DrawGeneratedPipe")
