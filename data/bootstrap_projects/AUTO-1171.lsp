(defun c:DrawGeneratedPipe ()
  (setq layer_name "ENG_AUTO-1171")
  (command "_.-LAYER" "_Make" layer_name "")
  (setvar "CLAYER" layer_name)
  (command "_.LINE" "0.000,0.000" "680.000,0.000" "")
  (command "_.CIRCLE" "0.000,0.000" "93.75")
  (command "_.ARC" "680.000,0.000" "680.000,187.500" "867.500,187.500")
  (command "_.TEXT" "887.500,-20.000" "5.0" "0" "EMPRESA: Engenharia CAD Labs")
  (command "_.TEXT" "887.500,-28.000" "5.0" "0" "PECA: Curva")
  (command "_.TEXT" "887.500,-36.000" "5.0" "0" "CODIGO: AUTO-1171")
  (princ "\nProjeto gerado com sucesso.")
)
(princ "\nComando carregado: DrawGeneratedPipe")
