(defun c:DrawGeneratedPipe ()
  (setq layer_name "ENG_AUTO-0601")
  (command "_.-LAYER" "_Make" layer_name "")
  (setvar "CLAYER" layer_name)
  (command "_.LINE" "0.000,0.000" "1905.000,0.000" "")
  (command "_.CIRCLE" "0.000,0.000" "31.25")
  (command "_.ARC" "1905.000,0.000" "1905.000,62.500" "1967.500,62.500")
  (command "_.TEXT" "1987.500,-20.000" "5.0" "0" "EMPRESA: Engenharia CAD Labs")
  (command "_.TEXT" "1987.500,-28.000" "5.0" "0" "PECA: Curva")
  (command "_.TEXT" "1987.500,-36.000" "5.0" "0" "CODIGO: AUTO-0601")
  (princ "\nProjeto gerado com sucesso.")
)
(princ "\nComando carregado: DrawGeneratedPipe")
