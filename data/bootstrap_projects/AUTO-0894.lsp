(defun c:DrawGeneratedPipe ()
  (setq layer_name "ENG_AUTO-0894")
  (command "_.-LAYER" "_Make" layer_name "")
  (setvar "CLAYER" layer_name)
  (command "_.LINE" "0.000,0.000" "610.000,0.000" "")
  (command "_.CIRCLE" "0.000,0.000" "112.5")
  (command "_.ARC" "610.000,0.000" "610.000,225.000" "835.000,225.000")
  (command "_.TEXT" "855.000,-20.000" "5.0" "0" "EMPRESA: Atlas Engenharia")
  (command "_.TEXT" "855.000,-28.000" "5.0" "0" "PECA: Tubo")
  (command "_.TEXT" "855.000,-36.000" "5.0" "0" "CODIGO: AUTO-0894")
  (princ "\nProjeto gerado com sucesso.")
)
(princ "\nComando carregado: DrawGeneratedPipe")
