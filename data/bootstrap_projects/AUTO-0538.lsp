(defun c:DrawGeneratedPipe ()
  (setq layer_name "ENG_AUTO-0538")
  (command "_.-LAYER" "_Make" layer_name "")
  (setvar "CLAYER" layer_name)
  (command "_.LINE" "0.000,0.000" "1625.000,0.000" "")
  (command "_.CIRCLE" "0.000,0.000" "137.5")
  (command "_.ARC" "1625.000,0.000" "1625.000,275.000" "1900.000,275.000")
  (command "_.TEXT" "1920.000,-20.000" "5.0" "0" "EMPRESA: Montreal Plantas")
  (command "_.TEXT" "1920.000,-28.000" "5.0" "0" "PECA: Reducer")
  (command "_.TEXT" "1920.000,-36.000" "5.0" "0" "CODIGO: AUTO-0538")
  (princ "\nProjeto gerado com sucesso.")
)
(princ "\nComando carregado: DrawGeneratedPipe")
