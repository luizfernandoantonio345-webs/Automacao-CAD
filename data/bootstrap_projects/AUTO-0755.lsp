(defun c:DrawGeneratedPipe ()
  (setq layer_name "ENG_AUTO-0755")
  (command "_.-LAYER" "_Make" layer_name "")
  (setvar "CLAYER" layer_name)
  (command "_.LINE" "0.000,0.000" "1520.000,0.000" "")
  (command "_.CIRCLE" "0.000,0.000" "243.75")
  (command "_.ARC" "1520.000,0.000" "1520.000,487.500" "2007.500,487.500")
  (command "_.TEXT" "2027.500,-20.000" "5.0" "0" "EMPRESA: Omega Piping")
  (command "_.TEXT" "2027.500,-28.000" "5.0" "0" "PECA: Valve")
  (command "_.TEXT" "2027.500,-36.000" "5.0" "0" "CODIGO: AUTO-0755")
  (princ "\nProjeto gerado com sucesso.")
)
(princ "\nComando carregado: DrawGeneratedPipe")
