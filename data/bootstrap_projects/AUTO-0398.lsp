(defun c:DrawGeneratedPipe ()
  (setq layer_name "ENG_AUTO-0398")
  (command "_.-LAYER" "_Make" layer_name "")
  (setvar "CLAYER" layer_name)
  (command "_.LINE" "0.000,0.000" "575.000,0.000" "")
  (command "_.CIRCLE" "0.000,0.000" "262.5")
  (command "_.ARC" "575.000,0.000" "575.000,525.000" "1100.000,525.000")
  (command "_.TEXT" "1120.000,-20.000" "5.0" "0" "EMPRESA: Norte Tubulacoes")
  (command "_.TEXT" "1120.000,-28.000" "5.0" "0" "PECA: Tee")
  (command "_.TEXT" "1120.000,-36.000" "5.0" "0" "CODIGO: AUTO-0398")
  (princ "\nProjeto gerado com sucesso.")
)
(princ "\nComando carregado: DrawGeneratedPipe")
