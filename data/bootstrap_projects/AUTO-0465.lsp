(defun c:DrawGeneratedPipe ()
  (setq layer_name "ENG_AUTO-0465")
  (command "_.-LAYER" "_Make" layer_name "")
  (setvar "CLAYER" layer_name)
  (command "_.LINE" "0.000,0.000" "995.000,0.000" "")
  (command "_.CIRCLE" "0.000,0.000" "181.25")
  (command "_.ARC" "995.000,0.000" "995.000,362.500" "1357.500,362.500")
  (command "_.TEXT" "1377.500,-20.000" "5.0" "0" "EMPRESA: Sul Processos")
  (command "_.TEXT" "1377.500,-28.000" "5.0" "0" "PECA: Flange")
  (command "_.TEXT" "1377.500,-36.000" "5.0" "0" "CODIGO: AUTO-0465")
  (princ "\nProjeto gerado com sucesso.")
)
(princ "\nComando carregado: DrawGeneratedPipe")
