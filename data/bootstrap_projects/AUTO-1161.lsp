(defun c:DrawGeneratedPipe ()
  (setq layer_name "ENG_AUTO-1161")
  (command "_.-LAYER" "_Make" layer_name "")
  (setvar "CLAYER" layer_name)
  (command "_.LINE" "0.000,0.000" "330.000,0.000" "")
  (command "_.CIRCLE" "0.000,0.000" "31.25")
  (command "_.ARC" "330.000,0.000" "330.000,62.500" "392.500,62.500")
  (command "_.TEXT" "412.500,-20.000" "5.0" "0" "EMPRESA: Sul Processos")
  (command "_.TEXT" "412.500,-28.000" "5.0" "0" "PECA: Flange")
  (command "_.TEXT" "412.500,-36.000" "5.0" "0" "CODIGO: AUTO-1161")
  (princ "\nProjeto gerado com sucesso.")
)
(princ "\nComando carregado: DrawGeneratedPipe")
