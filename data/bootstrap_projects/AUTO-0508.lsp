(defun c:DrawGeneratedPipe ()
  (setq layer_name "ENG_AUTO-0508")
  (command "_.-LAYER" "_Make" layer_name "")
  (setvar "CLAYER" layer_name)
  (command "_.LINE" "0.000,0.000" "575.000,0.000" "")
  (command "_.CIRCLE" "0.000,0.000" "200.0")
  (command "_.ARC" "575.000,0.000" "575.000,400.000" "975.000,400.000")
  (command "_.TEXT" "995.000,-20.000" "5.0" "0" "EMPRESA: Montreal Plantas")
  (command "_.TEXT" "995.000,-28.000" "5.0" "0" "PECA: Reducer")
  (command "_.TEXT" "995.000,-36.000" "5.0" "0" "CODIGO: AUTO-0508")
  (princ "\nProjeto gerado com sucesso.")
)
(princ "\nComando carregado: DrawGeneratedPipe")
