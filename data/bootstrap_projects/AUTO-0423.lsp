(defun c:DrawGeneratedPipe ()
  (setq layer_name "ENG_AUTO-0423")
  (command "_.-LAYER" "_Make" layer_name "")
  (setvar "CLAYER" layer_name)
  (command "_.LINE" "0.000,0.000" "1450.000,0.000" "")
  (command "_.CIRCLE" "0.000,0.000" "168.75")
  (command "_.ARC" "1450.000,0.000" "1450.000,337.500" "1787.500,337.500")
  (command "_.TEXT" "1807.500,-20.000" "5.0" "0" "EMPRESA: Sul Processos")
  (command "_.TEXT" "1807.500,-28.000" "5.0" "0" "PECA: Flange")
  (command "_.TEXT" "1807.500,-36.000" "5.0" "0" "CODIGO: AUTO-0423")
  (princ "\nProjeto gerado com sucesso.")
)
(princ "\nComando carregado: DrawGeneratedPipe")
