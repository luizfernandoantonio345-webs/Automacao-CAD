(defun c:DrawGeneratedPipe ()
  (setq layer_name "ENG_AUTO-0902")
  (command "_.-LAYER" "_Make" layer_name "")
  (setvar "CLAYER" layer_name)
  (command "_.LINE" "0.000,0.000" "890.000,0.000" "")
  (command "_.CIRCLE" "0.000,0.000" "162.5")
  (command "_.ARC" "890.000,0.000" "890.000,325.000" "1215.000,325.000")
  (command "_.TEXT" "1235.000,-20.000" "5.0" "0" "EMPRESA: Norte Tubulacoes")
  (command "_.TEXT" "1235.000,-28.000" "5.0" "0" "PECA: Tee")
  (command "_.TEXT" "1235.000,-36.000" "5.0" "0" "CODIGO: AUTO-0902")
  (princ "\nProjeto gerado com sucesso.")
)
(princ "\nComando carregado: DrawGeneratedPipe")
