(defun c:DrawGeneratedPipe ()
  (setq layer_name "ENG_AUTO-0214")
  (command "_.-LAYER" "_Make" layer_name "")
  (setvar "CLAYER" layer_name)
  (command "_.LINE" "0.000,0.000" "1835.000,0.000" "")
  (command "_.CIRCLE" "0.000,0.000" "112.5")
  (command "_.ARC" "1835.000,0.000" "1835.000,225.000" "2060.000,225.000")
  (command "_.TEXT" "2080.000,-20.000" "5.0" "0" "EMPRESA: Montreal Plantas")
  (command "_.TEXT" "2080.000,-28.000" "5.0" "0" "PECA: Reducer")
  (command "_.TEXT" "2080.000,-36.000" "5.0" "0" "CODIGO: AUTO-0214")
  (princ "\nProjeto gerado com sucesso.")
)
(princ "\nComando carregado: DrawGeneratedPipe")
