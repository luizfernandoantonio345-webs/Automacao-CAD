(defun c:DrawGeneratedPipe ()
  (setq layer_name "ENG_AUTO-0054")
  (command "_.-LAYER" "_Make" layer_name "")
  (setvar "CLAYER" layer_name)
  (command "_.LINE" "0.000,0.000" "2010.000,0.000" "")
  (command "_.CIRCLE" "0.000,0.000" "112.5")
  (command "_.ARC" "2010.000,0.000" "2010.000,225.000" "2235.000,225.000")
  (command "_.TEXT" "2255.000,-20.000" "5.0" "0" "EMPRESA: Atlas Engenharia")
  (command "_.TEXT" "2255.000,-28.000" "5.0" "0" "PECA: Tubo")
  (command "_.TEXT" "2255.000,-36.000" "5.0" "0" "CODIGO: AUTO-0054")
  (princ "\nProjeto gerado com sucesso.")
)
(princ "\nComando carregado: DrawGeneratedPipe")
