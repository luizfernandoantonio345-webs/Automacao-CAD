(defun c:DrawGeneratedPipe ()
  (setq layer_name "ENG_AUTO-1063")
  (command "_.-LAYER" "_Make" layer_name "")
  (setvar "CLAYER" layer_name)
  (command "_.LINE" "0.000,0.000" "750.000,0.000" "")
  (command "_.CIRCLE" "0.000,0.000" "168.75")
  (command "_.ARC" "750.000,0.000" "750.000,337.500" "1087.500,337.500")
  (command "_.TEXT" "1107.500,-20.000" "5.0" "0" "EMPRESA: Engenharia CAD Labs")
  (command "_.TEXT" "1107.500,-28.000" "5.0" "0" "PECA: Curva")
  (command "_.TEXT" "1107.500,-36.000" "5.0" "0" "CODIGO: AUTO-1063")
  (princ "\nProjeto gerado com sucesso.")
)
(princ "\nComando carregado: DrawGeneratedPipe")
