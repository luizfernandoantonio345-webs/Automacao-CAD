(defun c:DrawGeneratedPipe ()
  (setq layer_name "ENG_AUTO-0378")
  (command "_.-LAYER" "_Make" layer_name "")
  (setvar "CLAYER" layer_name)
  (command "_.LINE" "0.000,0.000" "1800.000,0.000" "")
  (command "_.CIRCLE" "0.000,0.000" "137.5")
  (command "_.ARC" "1800.000,0.000" "1800.000,275.000" "2075.000,275.000")
  (command "_.TEXT" "2095.000,-20.000" "5.0" "0" "EMPRESA: Atlas Engenharia")
  (command "_.TEXT" "2095.000,-28.000" "5.0" "0" "PECA: Tubo")
  (command "_.TEXT" "2095.000,-36.000" "5.0" "0" "CODIGO: AUTO-0378")
  (princ "\nProjeto gerado com sucesso.")
)
(princ "\nComando carregado: DrawGeneratedPipe")
