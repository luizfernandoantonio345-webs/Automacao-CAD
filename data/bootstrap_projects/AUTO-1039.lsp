(defun c:DrawGeneratedPipe ()
  (setq layer_name "ENG_AUTO-1039")
  (command "_.-LAYER" "_Make" layer_name "")
  (setvar "CLAYER" layer_name)
  (command "_.LINE" "0.000,0.000" "1835.000,0.000" "")
  (command "_.CIRCLE" "0.000,0.000" "268.75")
  (command "_.ARC" "1835.000,0.000" "1835.000,537.500" "2372.500,537.500")
  (command "_.TEXT" "2392.500,-20.000" "5.0" "0" "EMPRESA: Engenharia CAD Labs")
  (command "_.TEXT" "2392.500,-28.000" "5.0" "0" "PECA: Curva")
  (command "_.TEXT" "2392.500,-36.000" "5.0" "0" "CODIGO: AUTO-1039")
  (princ "\nProjeto gerado com sucesso.")
)
(princ "\nComando carregado: DrawGeneratedPipe")
