(defun c:DrawGeneratedPipe ()
  (setq layer_name "ENG_AUTO-0563")
  (command "_.-LAYER" "_Make" layer_name "")
  (setvar "CLAYER" layer_name)
  (command "_.LINE" "0.000,0.000" "575.000,0.000" "")
  (command "_.CIRCLE" "0.000,0.000" "43.75")
  (command "_.ARC" "575.000,0.000" "575.000,87.500" "662.500,87.500")
  (command "_.TEXT" "682.500,-20.000" "5.0" "0" "EMPRESA: Omega Piping")
  (command "_.TEXT" "682.500,-28.000" "5.0" "0" "PECA: Valve")
  (command "_.TEXT" "682.500,-36.000" "5.0" "0" "CODIGO: AUTO-0563")
  (princ "\nProjeto gerado com sucesso.")
)
(princ "\nComando carregado: DrawGeneratedPipe")
