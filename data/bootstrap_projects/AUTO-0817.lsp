(defun c:DrawGeneratedPipe ()
  (setq layer_name "ENG_AUTO-0817")
  (command "_.-LAYER" "_Make" layer_name "")
  (setvar "CLAYER" layer_name)
  (command "_.LINE" "0.000,0.000" "1765.000,0.000" "")
  (command "_.CIRCLE" "0.000,0.000" "131.25")
  (command "_.ARC" "1765.000,0.000" "1765.000,262.500" "2027.500,262.500")
  (command "_.TEXT" "2047.500,-20.000" "5.0" "0" "EMPRESA: Engenharia CAD Labs")
  (command "_.TEXT" "2047.500,-28.000" "5.0" "0" "PECA: Curva")
  (command "_.TEXT" "2047.500,-36.000" "5.0" "0" "CODIGO: AUTO-0817")
  (princ "\nProjeto gerado com sucesso.")
)
(princ "\nComando carregado: DrawGeneratedPipe")
