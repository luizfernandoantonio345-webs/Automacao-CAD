(defun c:DrawGeneratedPipe ()
  (setq layer_name "ENG_AUTO-0287")
  (command "_.-LAYER" "_Make" layer_name "")
  (setvar "CLAYER" layer_name)
  (command "_.LINE" "0.000,0.000" "540.000,0.000" "")
  (command "_.CIRCLE" "0.000,0.000" "68.75")
  (command "_.ARC" "540.000,0.000" "540.000,137.500" "677.500,137.500")
  (command "_.TEXT" "697.500,-20.000" "5.0" "0" "EMPRESA: Omega Piping")
  (command "_.TEXT" "697.500,-28.000" "5.0" "0" "PECA: Valve")
  (command "_.TEXT" "697.500,-36.000" "5.0" "0" "CODIGO: AUTO-0287")
  (princ "\nProjeto gerado com sucesso.")
)
(princ "\nComando carregado: DrawGeneratedPipe")
