(defun c:DrawGeneratedPipe ()
  (setq layer_name "ENG_AUTO-0583")
  (command "_.-LAYER" "_Make" layer_name "")
  (setvar "CLAYER" layer_name)
  (command "_.LINE" "0.000,0.000" "1275.000,0.000" "")
  (command "_.CIRCLE" "0.000,0.000" "168.75")
  (command "_.ARC" "1275.000,0.000" "1275.000,337.500" "1612.500,337.500")
  (command "_.TEXT" "1632.500,-20.000" "5.0" "0" "EMPRESA: Engenharia CAD Labs")
  (command "_.TEXT" "1632.500,-28.000" "5.0" "0" "PECA: Curva")
  (command "_.TEXT" "1632.500,-36.000" "5.0" "0" "CODIGO: AUTO-0583")
  (princ "\nProjeto gerado com sucesso.")
)
(princ "\nComando carregado: DrawGeneratedPipe")
