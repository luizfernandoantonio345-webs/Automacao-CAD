(defun c:DrawGeneratedPipe ()
  (setq layer_name "ENG_AUTO-0914")
  (command "_.-LAYER" "_Make" layer_name "")
  (setvar "CLAYER" layer_name)
  (command "_.LINE" "0.000,0.000" "1310.000,0.000" "")
  (command "_.CIRCLE" "0.000,0.000" "237.5")
  (command "_.ARC" "1310.000,0.000" "1310.000,475.000" "1785.000,475.000")
  (command "_.TEXT" "1805.000,-20.000" "5.0" "0" "EMPRESA: Norte Tubulacoes")
  (command "_.TEXT" "1805.000,-28.000" "5.0" "0" "PECA: Tee")
  (command "_.TEXT" "1805.000,-36.000" "5.0" "0" "CODIGO: AUTO-0914")
  (princ "\nProjeto gerado com sucesso.")
)
(princ "\nComando carregado: DrawGeneratedPipe")
