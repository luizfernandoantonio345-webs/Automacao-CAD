(defun c:DrawGeneratedPipe ()
  (setq layer_name "ENG_AUTO-0500")
  (command "_.-LAYER" "_Make" layer_name "")
  (setvar "CLAYER" layer_name)
  (command "_.LINE" "0.000,0.000" "295.000,0.000" "")
  (command "_.CIRCLE" "0.000,0.000" "150.0")
  (command "_.ARC" "295.000,0.000" "295.000,300.000" "595.000,300.000")
  (command "_.TEXT" "615.000,-20.000" "5.0" "0" "EMPRESA: Norte Tubulacoes")
  (command "_.TEXT" "615.000,-28.000" "5.0" "0" "PECA: Tee")
  (command "_.TEXT" "615.000,-36.000" "5.0" "0" "CODIGO: AUTO-0500")
  (princ "\nProjeto gerado com sucesso.")
)
(princ "\nComando carregado: DrawGeneratedPipe")
