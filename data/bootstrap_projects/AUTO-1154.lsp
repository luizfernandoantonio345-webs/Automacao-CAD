(defun c:DrawGeneratedPipe ()
  (setq layer_name "ENG_AUTO-1154")
  (command "_.-LAYER" "_Make" layer_name "")
  (setvar "CLAYER" layer_name)
  (command "_.LINE" "0.000,0.000" "2010.000,0.000" "")
  (command "_.CIRCLE" "0.000,0.000" "237.5")
  (command "_.ARC" "2010.000,0.000" "2010.000,475.000" "2485.000,475.000")
  (command "_.TEXT" "2505.000,-20.000" "5.0" "0" "EMPRESA: Norte Tubulacoes")
  (command "_.TEXT" "2505.000,-28.000" "5.0" "0" "PECA: Tee")
  (command "_.TEXT" "2505.000,-36.000" "5.0" "0" "CODIGO: AUTO-1154")
  (princ "\nProjeto gerado com sucesso.")
)
(princ "\nComando carregado: DrawGeneratedPipe")
