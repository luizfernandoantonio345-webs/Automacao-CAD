(defun c:DrawGeneratedPipe ()
  (setq layer_name "ENG_AUTO-0270")
  (command "_.-LAYER" "_Make" layer_name "")
  (setvar "CLAYER" layer_name)
  (command "_.LINE" "0.000,0.000" "1870.000,0.000" "")
  (command "_.CIRCLE" "0.000,0.000" "212.5")
  (command "_.ARC" "1870.000,0.000" "1870.000,425.000" "2295.000,425.000")
  (command "_.TEXT" "2315.000,-20.000" "5.0" "0" "EMPRESA: Atlas Engenharia")
  (command "_.TEXT" "2315.000,-28.000" "5.0" "0" "PECA: Tubo")
  (command "_.TEXT" "2315.000,-36.000" "5.0" "0" "CODIGO: AUTO-0270")
  (princ "\nProjeto gerado com sucesso.")
)
(princ "\nComando carregado: DrawGeneratedPipe")
