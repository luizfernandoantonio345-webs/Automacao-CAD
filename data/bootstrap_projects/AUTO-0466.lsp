(defun c:DrawGeneratedPipe ()
  (setq layer_name "ENG_AUTO-0466")
  (command "_.-LAYER" "_Make" layer_name "")
  (setvar "CLAYER" layer_name)
  (command "_.LINE" "0.000,0.000" "1030.000,0.000" "")
  (command "_.CIRCLE" "0.000,0.000" "187.5")
  (command "_.ARC" "1030.000,0.000" "1030.000,375.000" "1405.000,375.000")
  (command "_.TEXT" "1425.000,-20.000" "5.0" "0" "EMPRESA: Montreal Plantas")
  (command "_.TEXT" "1425.000,-28.000" "5.0" "0" "PECA: Reducer")
  (command "_.TEXT" "1425.000,-36.000" "5.0" "0" "CODIGO: AUTO-0466")
  (princ "\nProjeto gerado com sucesso.")
)
(princ "\nComando carregado: DrawGeneratedPipe")
