(defun c:DrawGeneratedPipe ()
  (setq layer_name "ENG_AUTO-0437")
  (command "_.-LAYER" "_Make" layer_name "")
  (setvar "CLAYER" layer_name)
  (command "_.LINE" "0.000,0.000" "1940.000,0.000" "")
  (command "_.CIRCLE" "0.000,0.000" "256.25")
  (command "_.ARC" "1940.000,0.000" "1940.000,512.500" "2452.500,512.500")
  (command "_.TEXT" "2472.500,-20.000" "5.0" "0" "EMPRESA: Omega Piping")
  (command "_.TEXT" "2472.500,-28.000" "5.0" "0" "PECA: Valve")
  (command "_.TEXT" "2472.500,-36.000" "5.0" "0" "CODIGO: AUTO-0437")
  (princ "\nProjeto gerado com sucesso.")
)
(princ "\nComando carregado: DrawGeneratedPipe")
