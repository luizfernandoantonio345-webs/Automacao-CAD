(defun c:DrawGeneratedPipe ()
  (setq layer_name "ENG_AUTO-1164")
  (command "_.-LAYER" "_Make" layer_name "")
  (setvar "CLAYER" layer_name)
  (command "_.LINE" "0.000,0.000" "435.000,0.000" "")
  (command "_.CIRCLE" "0.000,0.000" "50.0")
  (command "_.ARC" "435.000,0.000" "435.000,100.000" "535.000,100.000")
  (command "_.TEXT" "555.000,-20.000" "5.0" "0" "EMPRESA: Atlas Engenharia")
  (command "_.TEXT" "555.000,-28.000" "5.0" "0" "PECA: Tubo")
  (command "_.TEXT" "555.000,-36.000" "5.0" "0" "CODIGO: AUTO-1164")
  (princ "\nProjeto gerado com sucesso.")
)
(princ "\nComando carregado: DrawGeneratedPipe")
