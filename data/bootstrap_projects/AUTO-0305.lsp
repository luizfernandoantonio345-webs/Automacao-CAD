(defun c:DrawGeneratedPipe ()
  (setq layer_name "ENG_AUTO-0305")
  (command "_.-LAYER" "_Make" layer_name "")
  (setvar "CLAYER" layer_name)
  (command "_.LINE" "0.000,0.000" "1170.000,0.000" "")
  (command "_.CIRCLE" "0.000,0.000" "181.25")
  (command "_.ARC" "1170.000,0.000" "1170.000,362.500" "1532.500,362.500")
  (command "_.TEXT" "1552.500,-20.000" "5.0" "0" "EMPRESA: Omega Piping")
  (command "_.TEXT" "1552.500,-28.000" "5.0" "0" "PECA: Valve")
  (command "_.TEXT" "1552.500,-36.000" "5.0" "0" "CODIGO: AUTO-0305")
  (princ "\nProjeto gerado com sucesso.")
)
(princ "\nComando carregado: DrawGeneratedPipe")
