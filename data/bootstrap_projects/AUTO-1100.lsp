(defun c:DrawGeneratedPipe ()
  (setq layer_name "ENG_AUTO-1100")
  (command "_.-LAYER" "_Make" layer_name "")
  (setvar "CLAYER" layer_name)
  (command "_.LINE" "0.000,0.000" "120.000,0.000" "")
  (command "_.CIRCLE" "0.000,0.000" "150.0")
  (command "_.ARC" "120.000,0.000" "120.000,300.000" "420.000,300.000")
  (command "_.TEXT" "440.000,-20.000" "5.0" "0" "EMPRESA: Norte Tubulacoes")
  (command "_.TEXT" "440.000,-28.000" "5.0" "0" "PECA: Tee")
  (command "_.TEXT" "440.000,-36.000" "5.0" "0" "CODIGO: AUTO-1100")
  (princ "\nProjeto gerado com sucesso.")
)
(princ "\nComando carregado: DrawGeneratedPipe")
