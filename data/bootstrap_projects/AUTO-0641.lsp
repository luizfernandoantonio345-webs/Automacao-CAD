(defun c:DrawGeneratedPipe ()
  (setq layer_name "ENG_AUTO-0641")
  (command "_.-LAYER" "_Make" layer_name "")
  (setvar "CLAYER" layer_name)
  (command "_.LINE" "0.000,0.000" "1380.000,0.000" "")
  (command "_.CIRCLE" "0.000,0.000" "31.25")
  (command "_.ARC" "1380.000,0.000" "1380.000,62.500" "1442.500,62.500")
  (command "_.TEXT" "1462.500,-20.000" "5.0" "0" "EMPRESA: Omega Piping")
  (command "_.TEXT" "1462.500,-28.000" "5.0" "0" "PECA: Valve")
  (command "_.TEXT" "1462.500,-36.000" "5.0" "0" "CODIGO: AUTO-0641")
  (princ "\nProjeto gerado com sucesso.")
)
(princ "\nComando carregado: DrawGeneratedPipe")
