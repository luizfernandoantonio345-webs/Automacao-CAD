(defun c:DrawGeneratedPipe ()
  (setq layer_name "ENG_AUTO-0052")
  (command "_.-LAYER" "_Make" layer_name "")
  (setvar "CLAYER" layer_name)
  (command "_.LINE" "0.000,0.000" "1940.000,0.000" "")
  (command "_.CIRCLE" "0.000,0.000" "100.0")
  (command "_.ARC" "1940.000,0.000" "1940.000,200.000" "2140.000,200.000")
  (command "_.TEXT" "2160.000,-20.000" "5.0" "0" "EMPRESA: Montreal Plantas")
  (command "_.TEXT" "2160.000,-28.000" "5.0" "0" "PECA: Reducer")
  (command "_.TEXT" "2160.000,-36.000" "5.0" "0" "CODIGO: AUTO-0052")
  (princ "\nProjeto gerado com sucesso.")
)
(princ "\nComando carregado: DrawGeneratedPipe")
