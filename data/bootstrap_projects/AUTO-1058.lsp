(defun c:DrawGeneratedPipe ()
  (setq layer_name "ENG_AUTO-1058")
  (command "_.-LAYER" "_Make" layer_name "")
  (setvar "CLAYER" layer_name)
  (command "_.LINE" "0.000,0.000" "575.000,0.000" "")
  (command "_.CIRCLE" "0.000,0.000" "137.5")
  (command "_.ARC" "575.000,0.000" "575.000,275.000" "850.000,275.000")
  (command "_.TEXT" "870.000,-20.000" "5.0" "0" "EMPRESA: Norte Tubulacoes")
  (command "_.TEXT" "870.000,-28.000" "5.0" "0" "PECA: Tee")
  (command "_.TEXT" "870.000,-36.000" "5.0" "0" "CODIGO: AUTO-1058")
  (princ "\nProjeto gerado com sucesso.")
)
(princ "\nComando carregado: DrawGeneratedPipe")
