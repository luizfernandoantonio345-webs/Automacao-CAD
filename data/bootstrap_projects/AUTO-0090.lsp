(defun c:DrawGeneratedPipe ()
  (setq layer_name "ENG_AUTO-0090")
  (command "_.-LAYER" "_Make" layer_name "")
  (setvar "CLAYER" layer_name)
  (command "_.LINE" "0.000,0.000" "1345.000,0.000" "")
  (command "_.CIRCLE" "0.000,0.000" "87.5")
  (command "_.ARC" "1345.000,0.000" "1345.000,175.000" "1520.000,175.000")
  (command "_.TEXT" "1540.000,-20.000" "5.0" "0" "EMPRESA: Atlas Engenharia")
  (command "_.TEXT" "1540.000,-28.000" "5.0" "0" "PECA: Tubo")
  (command "_.TEXT" "1540.000,-36.000" "5.0" "0" "CODIGO: AUTO-0090")
  (princ "\nProjeto gerado com sucesso.")
)
(princ "\nComando carregado: DrawGeneratedPipe")
