(defun c:DrawGeneratedPipe ()
  (setq layer_name "ENG_AUTO-0554")
  (command "_.-LAYER" "_Make" layer_name "")
  (setvar "CLAYER" layer_name)
  (command "_.LINE" "0.000,0.000" "260.000,0.000" "")
  (command "_.CIRCLE" "0.000,0.000" "237.5")
  (command "_.ARC" "260.000,0.000" "260.000,475.000" "735.000,475.000")
  (command "_.TEXT" "755.000,-20.000" "5.0" "0" "EMPRESA: Norte Tubulacoes")
  (command "_.TEXT" "755.000,-28.000" "5.0" "0" "PECA: Tee")
  (command "_.TEXT" "755.000,-36.000" "5.0" "0" "CODIGO: AUTO-0554")
  (princ "\nProjeto gerado com sucesso.")
)
(princ "\nComando carregado: DrawGeneratedPipe")
