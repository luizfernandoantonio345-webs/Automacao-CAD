(defun c:DrawGeneratedPipe ()
  (setq layer_name "ENG_AUTO-0216")
  (command "_.-LAYER" "_Make" layer_name "")
  (setvar "CLAYER" layer_name)
  (command "_.LINE" "0.000,0.000" "1905.000,0.000" "")
  (command "_.CIRCLE" "0.000,0.000" "125.0")
  (command "_.ARC" "1905.000,0.000" "1905.000,250.000" "2155.000,250.000")
  (command "_.TEXT" "2175.000,-20.000" "5.0" "0" "EMPRESA: Atlas Engenharia")
  (command "_.TEXT" "2175.000,-28.000" "5.0" "0" "PECA: Tubo")
  (command "_.TEXT" "2175.000,-36.000" "5.0" "0" "CODIGO: AUTO-0216")
  (princ "\nProjeto gerado com sucesso.")
)
(princ "\nComando carregado: DrawGeneratedPipe")
