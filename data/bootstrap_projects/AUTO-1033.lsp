(defun c:DrawGeneratedPipe ()
  (setq layer_name "ENG_AUTO-1033")
  (command "_.-LAYER" "_Make" layer_name "")
  (setvar "CLAYER" layer_name)
  (command "_.LINE" "0.000,0.000" "1625.000,0.000" "")
  (command "_.CIRCLE" "0.000,0.000" "231.25")
  (command "_.ARC" "1625.000,0.000" "1625.000,462.500" "2087.500,462.500")
  (command "_.TEXT" "2107.500,-20.000" "5.0" "0" "EMPRESA: Engenharia CAD Labs")
  (command "_.TEXT" "2107.500,-28.000" "5.0" "0" "PECA: Curva")
  (command "_.TEXT" "2107.500,-36.000" "5.0" "0" "CODIGO: AUTO-1033")
  (princ "\nProjeto gerado com sucesso.")
)
(princ "\nComando carregado: DrawGeneratedPipe")
