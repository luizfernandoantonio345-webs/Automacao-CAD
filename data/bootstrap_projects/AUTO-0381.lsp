(defun c:DrawGeneratedPipe ()
  (setq layer_name "ENG_AUTO-0381")
  (command "_.-LAYER" "_Make" layer_name "")
  (setvar "CLAYER" layer_name)
  (command "_.LINE" "0.000,0.000" "1905.000,0.000" "")
  (command "_.CIRCLE" "0.000,0.000" "156.25")
  (command "_.ARC" "1905.000,0.000" "1905.000,312.500" "2217.500,312.500")
  (command "_.TEXT" "2237.500,-20.000" "5.0" "0" "EMPRESA: Sul Processos")
  (command "_.TEXT" "2237.500,-28.000" "5.0" "0" "PECA: Flange")
  (command "_.TEXT" "2237.500,-36.000" "5.0" "0" "CODIGO: AUTO-0381")
  (princ "\nProjeto gerado com sucesso.")
)
(princ "\nComando carregado: DrawGeneratedPipe")
