(defun c:DrawGeneratedPipe ()
  (setq layer_name "ENG_AUTO-1038")
  (command "_.-LAYER" "_Make" layer_name "")
  (setvar "CLAYER" layer_name)
  (command "_.LINE" "0.000,0.000" "1800.000,0.000" "")
  (command "_.CIRCLE" "0.000,0.000" "262.5")
  (command "_.ARC" "1800.000,0.000" "1800.000,525.000" "2325.000,525.000")
  (command "_.TEXT" "2345.000,-20.000" "5.0" "0" "EMPRESA: Atlas Engenharia")
  (command "_.TEXT" "2345.000,-28.000" "5.0" "0" "PECA: Tubo")
  (command "_.TEXT" "2345.000,-36.000" "5.0" "0" "CODIGO: AUTO-1038")
  (princ "\nProjeto gerado com sucesso.")
)
(princ "\nComando carregado: DrawGeneratedPipe")
