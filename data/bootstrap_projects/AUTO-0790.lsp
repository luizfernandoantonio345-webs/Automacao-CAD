(defun c:DrawGeneratedPipe ()
  (setq layer_name "ENG_AUTO-0790")
  (command "_.-LAYER" "_Make" layer_name "")
  (setvar "CLAYER" layer_name)
  (command "_.LINE" "0.000,0.000" "820.000,0.000" "")
  (command "_.CIRCLE" "0.000,0.000" "212.5")
  (command "_.ARC" "820.000,0.000" "820.000,425.000" "1245.000,425.000")
  (command "_.TEXT" "1265.000,-20.000" "5.0" "0" "EMPRESA: Montreal Plantas")
  (command "_.TEXT" "1265.000,-28.000" "5.0" "0" "PECA: Reducer")
  (command "_.TEXT" "1265.000,-36.000" "5.0" "0" "CODIGO: AUTO-0790")
  (princ "\nProjeto gerado com sucesso.")
)
(princ "\nComando carregado: DrawGeneratedPipe")
