(defun c:DrawGeneratedPipe ()
  (setq layer_name "ENG_AUTO-0736")
  (command "_.-LAYER" "_Make" layer_name "")
  (setvar "CLAYER" layer_name)
  (command "_.LINE" "0.000,0.000" "855.000,0.000" "")
  (command "_.CIRCLE" "0.000,0.000" "125.0")
  (command "_.ARC" "855.000,0.000" "855.000,250.000" "1105.000,250.000")
  (command "_.TEXT" "1125.000,-20.000" "5.0" "0" "EMPRESA: Montreal Plantas")
  (command "_.TEXT" "1125.000,-28.000" "5.0" "0" "PECA: Reducer")
  (command "_.TEXT" "1125.000,-36.000" "5.0" "0" "CODIGO: AUTO-0736")
  (princ "\nProjeto gerado com sucesso.")
)
(princ "\nComando carregado: DrawGeneratedPipe")
