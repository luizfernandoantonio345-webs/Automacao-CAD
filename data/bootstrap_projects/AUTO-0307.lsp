(defun c:DrawGeneratedPipe ()
  (setq layer_name "ENG_AUTO-0307")
  (command "_.-LAYER" "_Make" layer_name "")
  (setvar "CLAYER" layer_name)
  (command "_.LINE" "0.000,0.000" "1240.000,0.000" "")
  (command "_.CIRCLE" "0.000,0.000" "193.75")
  (command "_.ARC" "1240.000,0.000" "1240.000,387.500" "1627.500,387.500")
  (command "_.TEXT" "1647.500,-20.000" "5.0" "0" "EMPRESA: Engenharia CAD Labs")
  (command "_.TEXT" "1647.500,-28.000" "5.0" "0" "PECA: Curva")
  (command "_.TEXT" "1647.500,-36.000" "5.0" "0" "CODIGO: AUTO-0307")
  (princ "\nProjeto gerado com sucesso.")
)
(princ "\nComando carregado: DrawGeneratedPipe")
