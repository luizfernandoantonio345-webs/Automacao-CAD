(defun c:DrawGeneratedPipe ()
  (setq layer_name "ENG_AUTO-1047")
  (command "_.-LAYER" "_Make" layer_name "")
  (setvar "CLAYER" layer_name)
  (command "_.LINE" "0.000,0.000" "190.000,0.000" "")
  (command "_.CIRCLE" "0.000,0.000" "68.75")
  (command "_.ARC" "190.000,0.000" "190.000,137.500" "327.500,137.500")
  (command "_.TEXT" "347.500,-20.000" "5.0" "0" "EMPRESA: Sul Processos")
  (command "_.TEXT" "347.500,-28.000" "5.0" "0" "PECA: Flange")
  (command "_.TEXT" "347.500,-36.000" "5.0" "0" "CODIGO: AUTO-1047")
  (princ "\nProjeto gerado com sucesso.")
)
(princ "\nComando carregado: DrawGeneratedPipe")
