(defun c:DrawGeneratedPipe ()
  (setq layer_name "ENG_AUTO-1160")
  (command "_.-LAYER" "_Make" layer_name "")
  (setvar "CLAYER" layer_name)
  (command "_.LINE" "0.000,0.000" "295.000,0.000" "")
  (command "_.CIRCLE" "0.000,0.000" "25.0")
  (command "_.ARC" "295.000,0.000" "295.000,50.000" "345.000,50.000")
  (command "_.TEXT" "365.000,-20.000" "5.0" "0" "EMPRESA: Norte Tubulacoes")
  (command "_.TEXT" "365.000,-28.000" "5.0" "0" "PECA: Tee")
  (command "_.TEXT" "365.000,-36.000" "5.0" "0" "CODIGO: AUTO-1160")
  (princ "\nProjeto gerado com sucesso.")
)
(princ "\nComando carregado: DrawGeneratedPipe")
