(defun c:DrawGeneratedPipe ()
  (setq layer_name "ENG_AUTO-1174")
  (command "_.-LAYER" "_Make" layer_name "")
  (setvar "CLAYER" layer_name)
  (command "_.LINE" "0.000,0.000" "785.000,0.000" "")
  (command "_.CIRCLE" "0.000,0.000" "112.5")
  (command "_.ARC" "785.000,0.000" "785.000,225.000" "1010.000,225.000")
  (command "_.TEXT" "1030.000,-20.000" "5.0" "0" "EMPRESA: Montreal Plantas")
  (command "_.TEXT" "1030.000,-28.000" "5.0" "0" "PECA: Reducer")
  (command "_.TEXT" "1030.000,-36.000" "5.0" "0" "CODIGO: AUTO-1174")
  (princ "\nProjeto gerado com sucesso.")
)
(princ "\nComando carregado: DrawGeneratedPipe")
