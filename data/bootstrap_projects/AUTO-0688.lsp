(defun c:DrawGeneratedPipe ()
  (setq layer_name "ENG_AUTO-0688")
  (command "_.-LAYER" "_Make" layer_name "")
  (setvar "CLAYER" layer_name)
  (command "_.LINE" "0.000,0.000" "1100.000,0.000" "")
  (command "_.CIRCLE" "0.000,0.000" "75.0")
  (command "_.ARC" "1100.000,0.000" "1100.000,150.000" "1250.000,150.000")
  (command "_.TEXT" "1270.000,-20.000" "5.0" "0" "EMPRESA: Montreal Plantas")
  (command "_.TEXT" "1270.000,-28.000" "5.0" "0" "PECA: Reducer")
  (command "_.TEXT" "1270.000,-36.000" "5.0" "0" "CODIGO: AUTO-0688")
  (princ "\nProjeto gerado com sucesso.")
)
(princ "\nComando carregado: DrawGeneratedPipe")
