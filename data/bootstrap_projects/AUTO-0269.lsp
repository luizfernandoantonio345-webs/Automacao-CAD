(defun c:DrawGeneratedPipe ()
  (setq layer_name "ENG_AUTO-0269")
  (command "_.-LAYER" "_Make" layer_name "")
  (setvar "CLAYER" layer_name)
  (command "_.LINE" "0.000,0.000" "1835.000,0.000" "")
  (command "_.CIRCLE" "0.000,0.000" "206.25")
  (command "_.ARC" "1835.000,0.000" "1835.000,412.500" "2247.500,412.500")
  (command "_.TEXT" "2267.500,-20.000" "5.0" "0" "EMPRESA: Omega Piping")
  (command "_.TEXT" "2267.500,-28.000" "5.0" "0" "PECA: Valve")
  (command "_.TEXT" "2267.500,-36.000" "5.0" "0" "CODIGO: AUTO-0269")
  (princ "\nProjeto gerado com sucesso.")
)
(princ "\nComando carregado: DrawGeneratedPipe")
