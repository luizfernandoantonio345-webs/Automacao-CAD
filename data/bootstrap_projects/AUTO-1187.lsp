(defun c:DrawGeneratedPipe ()
  (setq layer_name "ENG_AUTO-1187")
  (command "_.-LAYER" "_Make" layer_name "")
  (setvar "CLAYER" layer_name)
  (command "_.LINE" "0.000,0.000" "1240.000,0.000" "")
  (command "_.CIRCLE" "0.000,0.000" "193.75")
  (command "_.ARC" "1240.000,0.000" "1240.000,387.500" "1627.500,387.500")
  (command "_.TEXT" "1647.500,-20.000" "5.0" "0" "EMPRESA: Omega Piping")
  (command "_.TEXT" "1647.500,-28.000" "5.0" "0" "PECA: Valve")
  (command "_.TEXT" "1647.500,-36.000" "5.0" "0" "CODIGO: AUTO-1187")
  (princ "\nProjeto gerado com sucesso.")
)
(princ "\nComando carregado: DrawGeneratedPipe")
