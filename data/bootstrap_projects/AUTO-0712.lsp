(defun c:DrawGeneratedPipe ()
  (setq layer_name "ENG_AUTO-0712")
  (command "_.-LAYER" "_Make" layer_name "")
  (setvar "CLAYER" layer_name)
  (command "_.LINE" "0.000,0.000" "1940.000,0.000" "")
  (command "_.CIRCLE" "0.000,0.000" "225.0")
  (command "_.ARC" "1940.000,0.000" "1940.000,450.000" "2390.000,450.000")
  (command "_.TEXT" "2410.000,-20.000" "5.0" "0" "EMPRESA: Montreal Plantas")
  (command "_.TEXT" "2410.000,-28.000" "5.0" "0" "PECA: Reducer")
  (command "_.TEXT" "2410.000,-36.000" "5.0" "0" "CODIGO: AUTO-0712")
  (princ "\nProjeto gerado com sucesso.")
)
(princ "\nComando carregado: DrawGeneratedPipe")
