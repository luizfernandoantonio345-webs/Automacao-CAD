(defun c:DrawGeneratedPipe ()
  (setq layer_name "ENG_AUTO-0980")
  (command "_.-LAYER" "_Make" layer_name "")
  (setvar "CLAYER" layer_name)
  (command "_.LINE" "0.000,0.000" "1695.000,0.000" "")
  (command "_.CIRCLE" "0.000,0.000" "150.0")
  (command "_.ARC" "1695.000,0.000" "1695.000,300.000" "1995.000,300.000")
  (command "_.TEXT" "2015.000,-20.000" "5.0" "0" "EMPRESA: Norte Tubulacoes")
  (command "_.TEXT" "2015.000,-28.000" "5.0" "0" "PECA: Tee")
  (command "_.TEXT" "2015.000,-36.000" "5.0" "0" "CODIGO: AUTO-0980")
  (princ "\nProjeto gerado com sucesso.")
)
(princ "\nComando carregado: DrawGeneratedPipe")
