(defun c:DrawGeneratedPipe ()
  (setq layer_name "ENG_AUTO-0322")
  (command "_.-LAYER" "_Make" layer_name "")
  (setvar "CLAYER" layer_name)
  (command "_.LINE" "0.000,0.000" "1765.000,0.000" "")
  (command "_.CIRCLE" "0.000,0.000" "37.5")
  (command "_.ARC" "1765.000,0.000" "1765.000,75.000" "1840.000,75.000")
  (command "_.TEXT" "1860.000,-20.000" "5.0" "0" "EMPRESA: Montreal Plantas")
  (command "_.TEXT" "1860.000,-28.000" "5.0" "0" "PECA: Reducer")
  (command "_.TEXT" "1860.000,-36.000" "5.0" "0" "CODIGO: AUTO-0322")
  (princ "\nProjeto gerado com sucesso.")
)
(princ "\nComando carregado: DrawGeneratedPipe")
