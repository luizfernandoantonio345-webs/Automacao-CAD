(defun c:DrawGeneratedPipe ()
  (setq layer_name "ENG_AUTO-0853")
  (command "_.-LAYER" "_Make" layer_name "")
  (setvar "CLAYER" layer_name)
  (command "_.LINE" "0.000,0.000" "1100.000,0.000" "")
  (command "_.CIRCLE" "0.000,0.000" "106.25")
  (command "_.ARC" "1100.000,0.000" "1100.000,212.500" "1312.500,212.500")
  (command "_.TEXT" "1332.500,-20.000" "5.0" "0" "EMPRESA: Engenharia CAD Labs")
  (command "_.TEXT" "1332.500,-28.000" "5.0" "0" "PECA: Curva")
  (command "_.TEXT" "1332.500,-36.000" "5.0" "0" "CODIGO: AUTO-0853")
  (princ "\nProjeto gerado com sucesso.")
)
(princ "\nComando carregado: DrawGeneratedPipe")
