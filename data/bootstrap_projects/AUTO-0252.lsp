(defun c:DrawGeneratedPipe ()
  (setq layer_name "ENG_AUTO-0252")
  (command "_.-LAYER" "_Make" layer_name "")
  (setvar "CLAYER" layer_name)
  (command "_.LINE" "0.000,0.000" "1240.000,0.000" "")
  (command "_.CIRCLE" "0.000,0.000" "100.0")
  (command "_.ARC" "1240.000,0.000" "1240.000,200.000" "1440.000,200.000")
  (command "_.TEXT" "1460.000,-20.000" "5.0" "0" "EMPRESA: Atlas Engenharia")
  (command "_.TEXT" "1460.000,-28.000" "5.0" "0" "PECA: Tubo")
  (command "_.TEXT" "1460.000,-36.000" "5.0" "0" "CODIGO: AUTO-0252")
  (princ "\nProjeto gerado com sucesso.")
)
(princ "\nComando carregado: DrawGeneratedPipe")
