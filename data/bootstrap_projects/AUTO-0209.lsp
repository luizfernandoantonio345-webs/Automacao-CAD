(defun c:DrawGeneratedPipe ()
  (setq layer_name "ENG_AUTO-0209")
  (command "_.-LAYER" "_Make" layer_name "")
  (setvar "CLAYER" layer_name)
  (command "_.LINE" "0.000,0.000" "1660.000,0.000" "")
  (command "_.CIRCLE" "0.000,0.000" "81.25")
  (command "_.ARC" "1660.000,0.000" "1660.000,162.500" "1822.500,162.500")
  (command "_.TEXT" "1842.500,-20.000" "5.0" "0" "EMPRESA: Omega Piping")
  (command "_.TEXT" "1842.500,-28.000" "5.0" "0" "PECA: Valve")
  (command "_.TEXT" "1842.500,-36.000" "5.0" "0" "CODIGO: AUTO-0209")
  (princ "\nProjeto gerado com sucesso.")
)
(princ "\nComando carregado: DrawGeneratedPipe")
