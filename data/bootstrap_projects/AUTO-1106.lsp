(defun c:DrawGeneratedPipe ()
  (setq layer_name "ENG_AUTO-1106")
  (command "_.-LAYER" "_Make" layer_name "")
  (setvar "CLAYER" layer_name)
  (command "_.LINE" "0.000,0.000" "330.000,0.000" "")
  (command "_.CIRCLE" "0.000,0.000" "187.5")
  (command "_.ARC" "330.000,0.000" "330.000,375.000" "705.000,375.000")
  (command "_.TEXT" "725.000,-20.000" "5.0" "0" "EMPRESA: Norte Tubulacoes")
  (command "_.TEXT" "725.000,-28.000" "5.0" "0" "PECA: Tee")
  (command "_.TEXT" "725.000,-36.000" "5.0" "0" "CODIGO: AUTO-1106")
  (princ "\nProjeto gerado com sucesso.")
)
(princ "\nComando carregado: DrawGeneratedPipe")
