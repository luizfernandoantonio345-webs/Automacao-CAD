(defun c:DrawGeneratedPipe ()
  (setq layer_name "ENG_AUTO-0734")
  (command "_.-LAYER" "_Make" layer_name "")
  (setvar "CLAYER" layer_name)
  (command "_.LINE" "0.000,0.000" "785.000,0.000" "")
  (command "_.CIRCLE" "0.000,0.000" "112.5")
  (command "_.ARC" "785.000,0.000" "785.000,225.000" "1010.000,225.000")
  (command "_.TEXT" "1030.000,-20.000" "5.0" "0" "EMPRESA: Norte Tubulacoes")
  (command "_.TEXT" "1030.000,-28.000" "5.0" "0" "PECA: Tee")
  (command "_.TEXT" "1030.000,-36.000" "5.0" "0" "CODIGO: AUTO-0734")
  (princ "\nProjeto gerado com sucesso.")
)
(princ "\nComando carregado: DrawGeneratedPipe")
