(defun c:DrawGeneratedPipe ()
  (setq layer_name "ENG_AUTO-0347")
  (command "_.-LAYER" "_Make" layer_name "")
  (setvar "CLAYER" layer_name)
  (command "_.LINE" "0.000,0.000" "715.000,0.000" "")
  (command "_.CIRCLE" "0.000,0.000" "193.75")
  (command "_.ARC" "715.000,0.000" "715.000,387.500" "1102.500,387.500")
  (command "_.TEXT" "1122.500,-20.000" "5.0" "0" "EMPRESA: Omega Piping")
  (command "_.TEXT" "1122.500,-28.000" "5.0" "0" "PECA: Valve")
  (command "_.TEXT" "1122.500,-36.000" "5.0" "0" "CODIGO: AUTO-0347")
  (princ "\nProjeto gerado com sucesso.")
)
(princ "\nComando carregado: DrawGeneratedPipe")
