(defun c:DrawGeneratedPipe ()
  (setq layer_name "ENG_AUTO-0186")
  (command "_.-LAYER" "_Make" layer_name "")
  (setvar "CLAYER" layer_name)
  (command "_.LINE" "0.000,0.000" "855.000,0.000" "")
  (command "_.CIRCLE" "0.000,0.000" "187.5")
  (command "_.ARC" "855.000,0.000" "855.000,375.000" "1230.000,375.000")
  (command "_.TEXT" "1250.000,-20.000" "5.0" "0" "EMPRESA: Atlas Engenharia")
  (command "_.TEXT" "1250.000,-28.000" "5.0" "0" "PECA: Tubo")
  (command "_.TEXT" "1250.000,-36.000" "5.0" "0" "CODIGO: AUTO-0186")
  (princ "\nProjeto gerado com sucesso.")
)
(princ "\nComando carregado: DrawGeneratedPipe")
