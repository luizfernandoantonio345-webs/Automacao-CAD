(defun c:DrawGeneratedPipe ()
  (setq layer_name "ENG_AUTO-0949")
  (command "_.-LAYER" "_Make" layer_name "")
  (setvar "CLAYER" layer_name)
  (command "_.LINE" "0.000,0.000" "610.000,0.000" "")
  (command "_.CIRCLE" "0.000,0.000" "206.25")
  (command "_.ARC" "610.000,0.000" "610.000,412.500" "1022.500,412.500")
  (command "_.TEXT" "1042.500,-20.000" "5.0" "0" "EMPRESA: Engenharia CAD Labs")
  (command "_.TEXT" "1042.500,-28.000" "5.0" "0" "PECA: Curva")
  (command "_.TEXT" "1042.500,-36.000" "5.0" "0" "CODIGO: AUTO-0949")
  (princ "\nProjeto gerado com sucesso.")
)
(princ "\nComando carregado: DrawGeneratedPipe")
