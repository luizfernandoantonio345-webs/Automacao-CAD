(defun c:DrawGeneratedPipe ()
  (setq layer_name "ENG_AUTO-0078")
  (command "_.-LAYER" "_Make" layer_name "")
  (setvar "CLAYER" layer_name)
  (command "_.LINE" "0.000,0.000" "925.000,0.000" "")
  (command "_.CIRCLE" "0.000,0.000" "262.5")
  (command "_.ARC" "925.000,0.000" "925.000,525.000" "1450.000,525.000")
  (command "_.TEXT" "1470.000,-20.000" "5.0" "0" "EMPRESA: Atlas Engenharia")
  (command "_.TEXT" "1470.000,-28.000" "5.0" "0" "PECA: Tubo")
  (command "_.TEXT" "1470.000,-36.000" "5.0" "0" "CODIGO: AUTO-0078")
  (princ "\nProjeto gerado com sucesso.")
)
(princ "\nComando carregado: DrawGeneratedPipe")
