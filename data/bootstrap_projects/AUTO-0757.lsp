(defun c:DrawGeneratedPipe ()
  (setq layer_name "ENG_AUTO-0757")
  (command "_.-LAYER" "_Make" layer_name "")
  (setvar "CLAYER" layer_name)
  (command "_.LINE" "0.000,0.000" "1590.000,0.000" "")
  (command "_.CIRCLE" "0.000,0.000" "256.25")
  (command "_.ARC" "1590.000,0.000" "1590.000,512.500" "2102.500,512.500")
  (command "_.TEXT" "2122.500,-20.000" "5.0" "0" "EMPRESA: Engenharia CAD Labs")
  (command "_.TEXT" "2122.500,-28.000" "5.0" "0" "PECA: Curva")
  (command "_.TEXT" "2122.500,-36.000" "5.0" "0" "CODIGO: AUTO-0757")
  (princ "\nProjeto gerado com sucesso.")
)
(princ "\nComando carregado: DrawGeneratedPipe")
