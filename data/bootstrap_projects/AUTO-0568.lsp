(defun c:DrawGeneratedPipe ()
  (setq layer_name "ENG_AUTO-0568")
  (command "_.-LAYER" "_Make" layer_name "")
  (setvar "CLAYER" layer_name)
  (command "_.LINE" "0.000,0.000" "750.000,0.000" "")
  (command "_.CIRCLE" "0.000,0.000" "75.0")
  (command "_.ARC" "750.000,0.000" "750.000,150.000" "900.000,150.000")
  (command "_.TEXT" "920.000,-20.000" "5.0" "0" "EMPRESA: Montreal Plantas")
  (command "_.TEXT" "920.000,-28.000" "5.0" "0" "PECA: Reducer")
  (command "_.TEXT" "920.000,-36.000" "5.0" "0" "CODIGO: AUTO-0568")
  (princ "\nProjeto gerado com sucesso.")
)
(princ "\nComando carregado: DrawGeneratedPipe")
