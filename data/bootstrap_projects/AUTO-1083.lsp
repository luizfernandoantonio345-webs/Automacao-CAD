(defun c:DrawGeneratedPipe ()
  (setq layer_name "ENG_AUTO-1083")
  (command "_.-LAYER" "_Make" layer_name "")
  (setvar "CLAYER" layer_name)
  (command "_.LINE" "0.000,0.000" "1450.000,0.000" "")
  (command "_.CIRCLE" "0.000,0.000" "43.75")
  (command "_.ARC" "1450.000,0.000" "1450.000,87.500" "1537.500,87.500")
  (command "_.TEXT" "1557.500,-20.000" "5.0" "0" "EMPRESA: Sul Processos")
  (command "_.TEXT" "1557.500,-28.000" "5.0" "0" "PECA: Flange")
  (command "_.TEXT" "1557.500,-36.000" "5.0" "0" "CODIGO: AUTO-1083")
  (princ "\nProjeto gerado com sucesso.")
)
(princ "\nComando carregado: DrawGeneratedPipe")
