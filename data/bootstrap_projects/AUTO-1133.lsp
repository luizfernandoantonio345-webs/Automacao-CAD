(defun c:DrawGeneratedPipe ()
  (setq layer_name "ENG_AUTO-1133")
  (command "_.-LAYER" "_Make" layer_name "")
  (setvar "CLAYER" layer_name)
  (command "_.LINE" "0.000,0.000" "1275.000,0.000" "")
  (command "_.CIRCLE" "0.000,0.000" "106.25")
  (command "_.ARC" "1275.000,0.000" "1275.000,212.500" "1487.500,212.500")
  (command "_.TEXT" "1507.500,-20.000" "5.0" "0" "EMPRESA: Omega Piping")
  (command "_.TEXT" "1507.500,-28.000" "5.0" "0" "PECA: Valve")
  (command "_.TEXT" "1507.500,-36.000" "5.0" "0" "CODIGO: AUTO-1133")
  (princ "\nProjeto gerado com sucesso.")
)
(princ "\nComando carregado: DrawGeneratedPipe")
