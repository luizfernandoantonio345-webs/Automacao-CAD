(defun c:DrawGeneratedPipe ()
  (setq layer_name "ENG_AUTO-0991")
  (command "_.-LAYER" "_Make" layer_name "")
  (setvar "CLAYER" layer_name)
  (command "_.LINE" "0.000,0.000" "155.000,0.000" "")
  (command "_.CIRCLE" "0.000,0.000" "218.75")
  (command "_.ARC" "155.000,0.000" "155.000,437.500" "592.500,437.500")
  (command "_.TEXT" "612.500,-20.000" "5.0" "0" "EMPRESA: Engenharia CAD Labs")
  (command "_.TEXT" "612.500,-28.000" "5.0" "0" "PECA: Curva")
  (command "_.TEXT" "612.500,-36.000" "5.0" "0" "CODIGO: AUTO-0991")
  (princ "\nProjeto gerado com sucesso.")
)
(princ "\nComando carregado: DrawGeneratedPipe")
