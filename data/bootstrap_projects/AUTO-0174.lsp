(defun c:DrawGeneratedPipe ()
  (setq layer_name "ENG_AUTO-0174")
  (command "_.-LAYER" "_Make" layer_name "")
  (setvar "CLAYER" layer_name)
  (command "_.LINE" "0.000,0.000" "435.000,0.000" "")
  (command "_.CIRCLE" "0.000,0.000" "112.5")
  (command "_.ARC" "435.000,0.000" "435.000,225.000" "660.000,225.000")
  (command "_.TEXT" "680.000,-20.000" "5.0" "0" "EMPRESA: Atlas Engenharia")
  (command "_.TEXT" "680.000,-28.000" "5.0" "0" "PECA: Tubo")
  (command "_.TEXT" "680.000,-36.000" "5.0" "0" "CODIGO: AUTO-0174")
  (princ "\nProjeto gerado com sucesso.")
)
(princ "\nComando carregado: DrawGeneratedPipe")
