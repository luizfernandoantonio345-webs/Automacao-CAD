(defun c:DrawGeneratedPipe ()
  (setq layer_name "ENG_AUTO-0909")
  (command "_.-LAYER" "_Make" layer_name "")
  (setvar "CLAYER" layer_name)
  (command "_.LINE" "0.000,0.000" "1135.000,0.000" "")
  (command "_.CIRCLE" "0.000,0.000" "206.25")
  (command "_.ARC" "1135.000,0.000" "1135.000,412.500" "1547.500,412.500")
  (command "_.TEXT" "1567.500,-20.000" "5.0" "0" "EMPRESA: Sul Processos")
  (command "_.TEXT" "1567.500,-28.000" "5.0" "0" "PECA: Flange")
  (command "_.TEXT" "1567.500,-36.000" "5.0" "0" "CODIGO: AUTO-0909")
  (princ "\nProjeto gerado com sucesso.")
)
(princ "\nComando carregado: DrawGeneratedPipe")
