(defun c:DrawGeneratedPipe ()
  (setq layer_name "ENG_AUTO-0977")
  (command "_.-LAYER" "_Make" layer_name "")
  (setvar "CLAYER" layer_name)
  (command "_.LINE" "0.000,0.000" "1590.000,0.000" "")
  (command "_.CIRCLE" "0.000,0.000" "131.25")
  (command "_.ARC" "1590.000,0.000" "1590.000,262.500" "1852.500,262.500")
  (command "_.TEXT" "1872.500,-20.000" "5.0" "0" "EMPRESA: Omega Piping")
  (command "_.TEXT" "1872.500,-28.000" "5.0" "0" "PECA: Valve")
  (command "_.TEXT" "1872.500,-36.000" "5.0" "0" "CODIGO: AUTO-0977")
  (princ "\nProjeto gerado com sucesso.")
)
(princ "\nComando carregado: DrawGeneratedPipe")
