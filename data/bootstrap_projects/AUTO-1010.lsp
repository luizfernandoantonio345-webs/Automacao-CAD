(defun c:DrawGeneratedPipe ()
  (setq layer_name "ENG_AUTO-1010")
  (command "_.-LAYER" "_Make" layer_name "")
  (setvar "CLAYER" layer_name)
  (command "_.LINE" "0.000,0.000" "820.000,0.000" "")
  (command "_.CIRCLE" "0.000,0.000" "87.5")
  (command "_.ARC" "820.000,0.000" "820.000,175.000" "995.000,175.000")
  (command "_.TEXT" "1015.000,-20.000" "5.0" "0" "EMPRESA: Norte Tubulacoes")
  (command "_.TEXT" "1015.000,-28.000" "5.0" "0" "PECA: Tee")
  (command "_.TEXT" "1015.000,-36.000" "5.0" "0" "CODIGO: AUTO-1010")
  (princ "\nProjeto gerado com sucesso.")
)
(princ "\nComando carregado: DrawGeneratedPipe")
