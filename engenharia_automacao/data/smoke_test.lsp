(defun c:GERAR_PROJETO ()
  (setq layer_name "CAD-001_ENG")
  (command "_.-LAYER" "_Make" layer_name "")
  (setvar "CLAYER" layer_name)
  (command "_.LINE" "0.000,0.000" "250.000,0.000" "")
  (command "_.CIRCLE" "0.000,0.000" "50.0" )
  (command "_.ARC" "250.000,0.000" "250.000,100.000" "350.000,100.000")
  (command "_.TEXT" "370.000,-20.000" "5" "0" "EMPRESA: Empresa Demo")
  (command "_.TEXT" "370.000,-28.000" "5" "0" "PECA: Peca Teste")
  (command "_.TEXT" "370.000,-36.000" "5" "0" "CODIGO: CAD-001")
  (princ "\nProjeto gerado com sucesso.")
)
(princ "\nComando carregado: GERAR_PROJETO")
